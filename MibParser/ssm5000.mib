MIB-MODULE DEFINITIONS ::= BEGIN
IMPORTS
	OBJECT-TYPE, MODULE-IDENTITY, enterprises, Integer32, Unsigned32 FROM SNMPv2-SMI
	IpAddress FROM RFC1155-SMI
	RowStatus, DateAndTime FROM SNMPv2-TC;

--- Module Identity

triadatv MODULE-IDENTITY
	LAST-UPDATED "08.06.2018 17:20:24"
	ORGANIZATION
		"OOO NPP Triada-TV"
	CONTACT-INFO
		"Nobosibirsk, Russia"
	DESCRIPTION
		""
::= { enterprises 31339 }

--- Node Definitions

Polaris-UNIFIED      OBJECT IDENTIFIER ::= { triadatv 20001 }
Polaris-SPECIFIC     OBJECT IDENTIFIER ::= { triadatv 42080 }
Polaris-System       OBJECT IDENTIFIER ::= { Polaris-SPECIFIC 1 }
Polaris-ControlUnits OBJECT IDENTIFIER ::= { Polaris-SPECIFIC 2 }
Polaris-Exciters     OBJECT IDENTIFIER ::= { Polaris-SPECIFIC 3 }
Polaris-Amplifiers   OBJECT IDENTIFIER ::= { Polaris-SPECIFIC 4 }
Polaris-Ssm          OBJECT IDENTIFIER ::= { Polaris-SPECIFIC 20 }
Polaris-Functions    OBJECT IDENTIFIER ::= { Polaris-SPECIFIC 21 }
PolarisTransmitter-Services OBJECT IDENTIFIER ::= { Polaris-Functions 2 }
fun-Display          OBJECT IDENTIFIER ::= { PolarisTransmitter-Services 1 }
fun-Controls         OBJECT IDENTIFIER ::= { PolarisTransmitter-Services 2 }
funCtl-PowerOut-Monitor OBJECT IDENTIFIER ::= { fun-Controls 1 }
funCtl-Misc          OBJECT IDENTIFIER ::= { fun-Controls 2 }
funDisp-Main         OBJECT IDENTIFIER ::= { fun-Display 1 }
funDisp-PowerOutMonitor OBJECT IDENTIFIER ::= { fun-Display 2 }
PolarisSsm-1         OBJECT IDENTIFIER ::= { Polaris-Ssm 1 }
ssm1-Unit            OBJECT IDENTIFIER ::= { PolarisSsm-1 1 }
ssm1-Auxiliary       OBJECT IDENTIFIER ::= { PolarisSsm-1 2 }
ssm1-Display         OBJECT IDENTIFIER ::= { PolarisSsm-1 3 }
ssm1-Output          OBJECT IDENTIFIER ::= { PolarisSsm-1 4 }
ssm1-TransmitterA    OBJECT IDENTIFIER ::= { PolarisSsm-1 5 }
ssm1-TransmitterB    OBJECT IDENTIFIER ::= { PolarisSsm-1 6 }
ssm1-TransmitterR    OBJECT IDENTIFIER ::= { PolarisSsm-1 7 }
ssm1-Control         OBJECT IDENTIFIER ::= { PolarisSsm-1 8 }
PolarisAmplifier-1   OBJECT IDENTIFIER ::= { Polaris-Amplifiers 1 }
PolarisAmplifier-2   OBJECT IDENTIFIER ::= { Polaris-Amplifiers 2 }
PolarisAmplifier-3   OBJECT IDENTIFIER ::= { Polaris-Amplifiers 3 }
PolarisAmplifier-4   OBJECT IDENTIFIER ::= { Polaris-Amplifiers 4 }
PolarisAmplifier-5   OBJECT IDENTIFIER ::= { Polaris-Amplifiers 5 }
PolarisAmplifier-6   OBJECT IDENTIFIER ::= { Polaris-Amplifiers 6 }
PolarisAmplifier-7   OBJECT IDENTIFIER ::= { Polaris-Amplifiers 7 }
PolarisAmplifier-8   OBJECT IDENTIFIER ::= { Polaris-Amplifiers 8 }
amp8-Unit            OBJECT IDENTIFIER ::= { PolarisAmplifier-8 1 }
amp8-Auxiliary       OBJECT IDENTIFIER ::= { PolarisAmplifier-8 2 }
amp8-Display         OBJECT IDENTIFIER ::= { PolarisAmplifier-8 3 }
amp8Disp-Main        OBJECT IDENTIFIER ::= { amp8-Display 1 }
amp8Disp-Temperatures OBJECT IDENTIFIER ::= { amp8-Display 2 }
amp8Disp-Currents    OBJECT IDENTIFIER ::= { amp8-Display 3 }
amp8Disp-Currents-Dividers OBJECT IDENTIFIER ::= { amp8-Display 4 }
amp7-Unit            OBJECT IDENTIFIER ::= { PolarisAmplifier-7 1 }
amp7-Auxiliary       OBJECT IDENTIFIER ::= { PolarisAmplifier-7 2 }
amp7-Display         OBJECT IDENTIFIER ::= { PolarisAmplifier-7 3 }
amp7Disp-Main        OBJECT IDENTIFIER ::= { amp7-Display 1 }
amp7Disp-Temperatures OBJECT IDENTIFIER ::= { amp7-Display 2 }
amp7Disp-Currents    OBJECT IDENTIFIER ::= { amp7-Display 3 }
amp7Disp-Currents-Dividers OBJECT IDENTIFIER ::= { amp7-Display 4 }
amp6-Unit            OBJECT IDENTIFIER ::= { PolarisAmplifier-6 1 }
amp6-Auxiliary       OBJECT IDENTIFIER ::= { PolarisAmplifier-6 2 }
amp6-Display         OBJECT IDENTIFIER ::= { PolarisAmplifier-6 3 }
amp6Disp-Main        OBJECT IDENTIFIER ::= { amp6-Display 1 }
amp6Disp-Temperatures OBJECT IDENTIFIER ::= { amp6-Display 2 }
amp6Disp-Currents    OBJECT IDENTIFIER ::= { amp6-Display 3 }
amp6Disp-Currents-Dividers OBJECT IDENTIFIER ::= { amp6-Display 4 }
amp5-Unit            OBJECT IDENTIFIER ::= { PolarisAmplifier-5 1 }
amp5-Auxiliary       OBJECT IDENTIFIER ::= { PolarisAmplifier-5 2 }
amp5-Display         OBJECT IDENTIFIER ::= { PolarisAmplifier-5 3 }
amp5Disp-Main        OBJECT IDENTIFIER ::= { amp5-Display 1 }
amp5Disp-Temperatures OBJECT IDENTIFIER ::= { amp5-Display 2 }
amp5Disp-Currents    OBJECT IDENTIFIER ::= { amp5-Display 3 }
amp5Disp-Currents-Dividers OBJECT IDENTIFIER ::= { amp5-Display 4 }
amp4-Unit            OBJECT IDENTIFIER ::= { PolarisAmplifier-4 1 }
amp4-Auxiliary       OBJECT IDENTIFIER ::= { PolarisAmplifier-4 2 }
amp4-Display         OBJECT IDENTIFIER ::= { PolarisAmplifier-4 3 }
amp4Disp-Main        OBJECT IDENTIFIER ::= { amp4-Display 1 }
amp4Disp-Temperatures OBJECT IDENTIFIER ::= { amp4-Display 2 }
amp4Disp-Currents    OBJECT IDENTIFIER ::= { amp4-Display 3 }
amp4Disp-Currents-Dividers OBJECT IDENTIFIER ::= { amp4-Display 4 }
amp3-Unit            OBJECT IDENTIFIER ::= { PolarisAmplifier-3 1 }
amp3-Auxiliary       OBJECT IDENTIFIER ::= { PolarisAmplifier-3 2 }
amp3-Display         OBJECT IDENTIFIER ::= { PolarisAmplifier-3 3 }
amp3Disp-Main        OBJECT IDENTIFIER ::= { amp3-Display 1 }
amp3Disp-Temperatures OBJECT IDENTIFIER ::= { amp3-Display 2 }
amp3Disp-Currents    OBJECT IDENTIFIER ::= { amp3-Display 3 }
amp3Disp-Currents-Dividers OBJECT IDENTIFIER ::= { amp3-Display 4 }
amp2-Unit            OBJECT IDENTIFIER ::= { PolarisAmplifier-2 1 }
amp2-Auxiliary       OBJECT IDENTIFIER ::= { PolarisAmplifier-2 2 }
amp2-Display         OBJECT IDENTIFIER ::= { PolarisAmplifier-2 3 }
amp2Disp-Main        OBJECT IDENTIFIER ::= { amp2-Display 1 }
amp2Disp-Temperatures OBJECT IDENTIFIER ::= { amp2-Display 2 }
amp2Disp-Currents    OBJECT IDENTIFIER ::= { amp2-Display 3 }
amp2Disp-Currents-Dividers OBJECT IDENTIFIER ::= { amp2-Display 4 }
amp1-Unit            OBJECT IDENTIFIER ::= { PolarisAmplifier-1 1 }
amp1-Auxiliary       OBJECT IDENTIFIER ::= { PolarisAmplifier-1 2 }
amp1-Display         OBJECT IDENTIFIER ::= { PolarisAmplifier-1 3 }
amp1Disp-Main        OBJECT IDENTIFIER ::= { amp1-Display 1 }
amp1Disp-Temperatures OBJECT IDENTIFIER ::= { amp1-Display 2 }
amp1Disp-Currents    OBJECT IDENTIFIER ::= { amp1-Display 3 }
amp1Disp-Currents-Dividers OBJECT IDENTIFIER ::= { amp1-Display 4 }
PolarisExciter-1     OBJECT IDENTIFIER ::= { Polaris-Exciters 1 }
PolarisExciter-2     OBJECT IDENTIFIER ::= { Polaris-Exciters 2 }
exc2-Unit            OBJECT IDENTIFIER ::= { PolarisExciter-2 1 }
exc2-Auxiliary       OBJECT IDENTIFIER ::= { PolarisExciter-2 2 }
exc2-Display         OBJECT IDENTIFIER ::= { PolarisExciter-2 3 }
exc2-Parameters      OBJECT IDENTIFIER ::= { PolarisExciter-2 4 }
exc2-Messages        OBJECT IDENTIFIER ::= { PolarisExciter-2 5 }
exc2-Unified         OBJECT IDENTIFIER ::= { PolarisExciter-2 6 }
exc2-Param-Monitoring OBJECT IDENTIFIER ::= { exc2-Parameters 1 }
exc2-Param-Reference OBJECT IDENTIFIER ::= { exc2-Parameters 2 }
exc2-Param-Glonass-GPS OBJECT IDENTIFIER ::= { exc2-Parameters 3 }
exc2-Param-Input     OBJECT IDENTIFIER ::= { exc2-Parameters 4 }
exc2-Param-Output    OBJECT IDENTIFIER ::= { exc2-Parameters 5 }
exc2-Param-DVB-T     OBJECT IDENTIFIER ::= { exc2-Parameters 6 }
exc2-Param-DVB-T2    OBJECT IDENTIFIER ::= { exc2-Parameters 7 }
exc2-Param-Tests     OBJECT IDENTIFIER ::= { exc2-Parameters 8 }
exc2-Param-Service   OBJECT IDENTIFIER ::= { exc2-Parameters 9 }
exc2-Param-Firmware  OBJECT IDENTIFIER ::= { exc2-Parameters 10 }
exc2-Param-Precorrection OBJECT IDENTIFIER ::= { exc2-Parameters 11 }
exc2-Param-Precorrection-Non-Linear OBJECT IDENTIFIER ::= { exc2-Param-Precorrection 1 }
exc2-Param-Precorrection-Linear OBJECT IDENTIFIER ::= { exc2-Param-Precorrection 2 }
exc2-Param-Precorrection-Lin-Monitoring OBJECT IDENTIFIER ::= { exc2-Param-Precorrection-Linear 1 }
exc2-Param-Precorrection-Lin-Control OBJECT IDENTIFIER ::= { exc2-Param-Precorrection-Linear 2 }
exc2-Param-Precorrection-NonLin-Monitoring OBJECT IDENTIFIER ::= { exc2-Param-Precorrection-Non-Linear 1 }
exc2-Param-Precorrection-NonLin-Control OBJECT IDENTIFIER ::= { exc2-Param-Precorrection-Non-Linear 2 }
exc2-Param-Service-Monitoring OBJECT IDENTIFIER ::= { exc2-Param-Service 1 }
exc2-Param-Service-Control OBJECT IDENTIFIER ::= { exc2-Param-Service 2 }
exc2-Param-T2-SFN    OBJECT IDENTIFIER ::= { exc2-Param-DVB-T2 1 }
exc2-Param-T2-InputStream OBJECT IDENTIFIER ::= { exc2-Param-DVB-T2 2 }
exc2-Param-T2-Settings OBJECT IDENTIFIER ::= { exc2-Param-DVB-T2 3 }
exc2-Param-T2-PLP    OBJECT IDENTIFIER ::= { exc2-Param-DVB-T2 4 }
exc2-Param-T2-PLP-System-A OBJECT IDENTIFIER ::= { exc2-Param-T2-PLP 1 }
exc2-Param-T2-PLP-System-B OBJECT IDENTIFIER ::= { exc2-Param-T2-PLP 2 }
exc2-Param-T2-PLP-B-Table OBJECT IDENTIFIER ::= { exc2-Param-T2-PLP-System-B 2 }
exc2-Param-T2-PLP-B-Column-1 OBJECT IDENTIFIER ::= { exc2-Param-T2-PLP-B-Table 1 }
exc2-Param-T2-PLP-B-Column-2 OBJECT IDENTIFIER ::= { exc2-Param-T2-PLP-B-Table 2 }
exc2-Param-T2-PLP-B-Column-3 OBJECT IDENTIFIER ::= { exc2-Param-T2-PLP-B-Table 3 }
exc2-Param-T2-PLP-B-Column-4 OBJECT IDENTIFIER ::= { exc2-Param-T2-PLP-B-Table 4 }
exc2-Param-T2-PLP-B-Column-5 OBJECT IDENTIFIER ::= { exc2-Param-T2-PLP-B-Table 5 }
exc2-Param-T2-PLP-B-Column-6 OBJECT IDENTIFIER ::= { exc2-Param-T2-PLP-B-Table 6 }
exc2-Param-T2-PLP-B-Column-7 OBJECT IDENTIFIER ::= { exc2-Param-T2-PLP-B-Table 7 }
exc2-Param-T2-PLP-B-Column-8 OBJECT IDENTIFIER ::= { exc2-Param-T2-PLP-B-Table 8 }
exc2-Param-T2-PLP-B-Column-9 OBJECT IDENTIFIER ::= { exc2-Param-T2-PLP-B-Table 9 }
exc2-Param-T2-PLP-B-Column-10 OBJECT IDENTIFIER ::= { exc2-Param-T2-PLP-B-Table 10 }
exc2-Param-T2-PLP-B-Column-11 OBJECT IDENTIFIER ::= { exc2-Param-T2-PLP-B-Table 11 }
exc2-Param-T2-PLP-B-Column-12 OBJECT IDENTIFIER ::= { exc2-Param-T2-PLP-B-Table 12 }
exc2-Param-T2-PLP-B-Column-13 OBJECT IDENTIFIER ::= { exc2-Param-T2-PLP-B-Table 13 }
exc2-Param-T2-PLP-B-Column-14 OBJECT IDENTIFIER ::= { exc2-Param-T2-PLP-B-Table 14 }
exc2-Param-T2-PLP-B-Column-15 OBJECT IDENTIFIER ::= { exc2-Param-T2-PLP-B-Table 15 }
exc2-Param-T2-PLP-B-Column-16 OBJECT IDENTIFIER ::= { exc2-Param-T2-PLP-B-Table 16 }
exc2-Param-T2-Settings-Frame-Modulation OBJECT IDENTIFIER ::= { exc2-Param-T2-Settings 1 }
exc2-Param-T2-Settings-Frame-Structure OBJECT IDENTIFIER ::= { exc2-Param-T2-Settings 2 }
exc2-Param-T2-Settings-PAPR OBJECT IDENTIFIER ::= { exc2-Param-T2-Settings 3 }
exc2-Param-T2-Settings-Network OBJECT IDENTIFIER ::= { exc2-Param-T2-Settings 4 }
exc2-Param-T-MFN     OBJECT IDENTIFIER ::= { exc2-Param-DVB-T 1 }
exc2-Param-T-SFN     OBJECT IDENTIFIER ::= { exc2-Param-DVB-T 2 }
exc2-Param-T-Mode    OBJECT IDENTIFIER ::= { exc2-Param-DVB-T 3 }
exc2-Param-T-TPS     OBJECT IDENTIFIER ::= { exc2-Param-DVB-T 4 }
exc2-Param-T-Specific-Config OBJECT IDENTIFIER ::= { exc2-Param-DVB-T 5 }
exc2-Param-T-MIP-Control OBJECT IDENTIFIER ::= { exc2-Param-DVB-T 6 }
exc2-Param-Input-Main OBJECT IDENTIFIER ::= { exc2-Param-Input 1 }
exc2-Param-Input-Clever-Parameters OBJECT IDENTIFIER ::= { exc2-Param-Input 2 }
exc2-Param-Input-IP-1-Control OBJECT IDENTIFIER ::= { exc2-Param-Input 3 }
exc2-Param-Input-IP-2-Control OBJECT IDENTIFIER ::= { exc2-Param-Input 4 }
exc2-Param-Input-IP-1-RX OBJECT IDENTIFIER ::= { exc2-Param-Input 5 }
exc2-Param-Input-IP-2-RX OBJECT IDENTIFIER ::= { exc2-Param-Input 6 }
exc2-Param-Input-IP-1-IGMP OBJECT IDENTIFIER ::= { exc2-Param-Input 7 }
exc2-Param-Input-IP-2-IGMP OBJECT IDENTIFIER ::= { exc2-Param-Input 8 }
exc2-Param-Input-Clever-Switch-IP-Parameters OBJECT IDENTIFIER ::= { exc2-Param-Input 9 }
exc2-Param-Glonass-GPS-Monitoring OBJECT IDENTIFIER ::= { exc2-Param-Glonass-GPS 1 }
exc2-Param-Glonass-GPS-Control OBJECT IDENTIFIER ::= { exc2-Param-Glonass-GPS 2 }
exc2-Param-Mon-Main  OBJECT IDENTIFIER ::= { exc2-Param-Monitoring 1 }
exc2-Param-Mon-Stream1 OBJECT IDENTIFIER ::= { exc2-Param-Monitoring 2 }
exc2-Param-Mon-Stream2 OBJECT IDENTIFIER ::= { exc2-Param-Monitoring 3 }
exc2-Param-Mon-Clever-Status OBJECT IDENTIFIER ::= { exc2-Param-Monitoring 4 }
exc2-Param-Mon-ASI   OBJECT IDENTIFIER ::= { exc2-Param-Monitoring 5 }
exc2-Param-Mon-IP-Inputs OBJECT IDENTIFIER ::= { exc2-Param-Monitoring 6 }
exc2-Param-Mon-Clever-Switch-IP-Status OBJECT IDENTIFIER ::= { exc2-Param-Monitoring 7 }
exc2-Param-Mon-IP-Input-Status OBJECT IDENTIFIER ::= { exc2-Param-Mon-IP-Inputs 1 }
exc2-Param-Mon-IP-IP-1-Status OBJECT IDENTIFIER ::= { exc2-Param-Mon-IP-Inputs 2 }
exc2-Param-Mon-IP-IP-2-Status OBJECT IDENTIFIER ::= { exc2-Param-Mon-IP-Inputs 3 }
exc2-Param-Mon-IP-IP-1-RX-Status OBJECT IDENTIFIER ::= { exc2-Param-Mon-IP-Inputs 4 }
exc2-Param-Mon-IP-IP-2-RX-Status OBJECT IDENTIFIER ::= { exc2-Param-Mon-IP-Inputs 5 }
exc2-Param-Mon-ASI-1-Status OBJECT IDENTIFIER ::= { exc2-Param-Mon-ASI 1 }
exc2-Param-Mon-ASI-2-Status OBJECT IDENTIFIER ::= { exc2-Param-Mon-ASI 2 }
exc2-Display-Main    OBJECT IDENTIFIER ::= { exc2-Display 1 }
exc2-Aux-Connected   OBJECT IDENTIFIER ::= { exc2-Auxiliary 1 }
exc2-Aux-Processing  OBJECT IDENTIFIER ::= { exc2-Auxiliary 2 }
exc2-Aux-Values      OBJECT IDENTIFIER ::= { exc2-Auxiliary 3 }
exc2-Aux-Options     OBJECT IDENTIFIER ::= { exc2-Auxiliary 4 }
exc2-Aux-Commands    OBJECT IDENTIFIER ::= { exc2-Auxiliary 5 }
exc1-Unit            OBJECT IDENTIFIER ::= { PolarisExciter-1 1 }
exc1-Auxiliary       OBJECT IDENTIFIER ::= { PolarisExciter-1 2 }
exc1-Display         OBJECT IDENTIFIER ::= { PolarisExciter-1 3 }
exc1-Parameters      OBJECT IDENTIFIER ::= { PolarisExciter-1 4 }
exc1-Messages        OBJECT IDENTIFIER ::= { PolarisExciter-1 5 }
exc1-Unified         OBJECT IDENTIFIER ::= { PolarisExciter-1 6 }
exc1-Param-Monitoring OBJECT IDENTIFIER ::= { exc1-Parameters 1 }
exc1-Param-Reference OBJECT IDENTIFIER ::= { exc1-Parameters 2 }
exc1-Param-Glonass-GPS OBJECT IDENTIFIER ::= { exc1-Parameters 3 }
exc1-Param-Input     OBJECT IDENTIFIER ::= { exc1-Parameters 4 }
exc1-Param-Output    OBJECT IDENTIFIER ::= { exc1-Parameters 5 }
exc1-Param-DVB-T     OBJECT IDENTIFIER ::= { exc1-Parameters 6 }
exc1-Param-DVB-T2    OBJECT IDENTIFIER ::= { exc1-Parameters 7 }
exc1-Param-Tests     OBJECT IDENTIFIER ::= { exc1-Parameters 8 }
exc1-Param-Service   OBJECT IDENTIFIER ::= { exc1-Parameters 9 }
exc1-Param-Firmware  OBJECT IDENTIFIER ::= { exc1-Parameters 10 }
exc1-Param-Precorrection OBJECT IDENTIFIER ::= { exc1-Parameters 11 }
exc1-Param-Precorrection-Non-Linear OBJECT IDENTIFIER ::= { exc1-Param-Precorrection 1 }
exc1-Param-Precorrection-Linear OBJECT IDENTIFIER ::= { exc1-Param-Precorrection 2 }
exc1-Param-Precorrection-Lin-Monitoring OBJECT IDENTIFIER ::= { exc1-Param-Precorrection-Linear 1 }
exc1-Param-Precorrection-Lin-Control OBJECT IDENTIFIER ::= { exc1-Param-Precorrection-Linear 2 }
exc1-Param-Precorrection-NonLin-Monitoring OBJECT IDENTIFIER ::= { exc1-Param-Precorrection-Non-Linear 1 }
exc1-Param-Precorrection-NonLin-Control OBJECT IDENTIFIER ::= { exc1-Param-Precorrection-Non-Linear 2 }
exc1-Param-Service-Monitoring OBJECT IDENTIFIER ::= { exc1-Param-Service 1 }
exc1-Param-Service-Control OBJECT IDENTIFIER ::= { exc1-Param-Service 2 }
exc1-Param-T2-SFN    OBJECT IDENTIFIER ::= { exc1-Param-DVB-T2 1 }
exc1-Param-T2-InputStream OBJECT IDENTIFIER ::= { exc1-Param-DVB-T2 2 }
exc1-Param-T2-Settings OBJECT IDENTIFIER ::= { exc1-Param-DVB-T2 3 }
exc1-Param-T2-PLP    OBJECT IDENTIFIER ::= { exc1-Param-DVB-T2 4 }
exc1-Param-T2-PLP-System-A OBJECT IDENTIFIER ::= { exc1-Param-T2-PLP 1 }
exc1-Param-T2-PLP-System-B OBJECT IDENTIFIER ::= { exc1-Param-T2-PLP 2 }
exc1-Param-T2-PLP-B-Table OBJECT IDENTIFIER ::= { exc1-Param-T2-PLP-System-B 2 }
exc1-Param-T2-PLP-B-Column-1 OBJECT IDENTIFIER ::= { exc1-Param-T2-PLP-B-Table 1 }
exc1-Param-T2-PLP-B-Column-2 OBJECT IDENTIFIER ::= { exc1-Param-T2-PLP-B-Table 2 }
exc1-Param-T2-PLP-B-Column-3 OBJECT IDENTIFIER ::= { exc1-Param-T2-PLP-B-Table 3 }
exc1-Param-T2-PLP-B-Column-4 OBJECT IDENTIFIER ::= { exc1-Param-T2-PLP-B-Table 4 }
exc1-Param-T2-PLP-B-Column-5 OBJECT IDENTIFIER ::= { exc1-Param-T2-PLP-B-Table 5 }
exc1-Param-T2-PLP-B-Column-6 OBJECT IDENTIFIER ::= { exc1-Param-T2-PLP-B-Table 6 }
exc1-Param-T2-PLP-B-Column-7 OBJECT IDENTIFIER ::= { exc1-Param-T2-PLP-B-Table 7 }
exc1-Param-T2-PLP-B-Column-8 OBJECT IDENTIFIER ::= { exc1-Param-T2-PLP-B-Table 8 }
exc1-Param-T2-PLP-B-Column-9 OBJECT IDENTIFIER ::= { exc1-Param-T2-PLP-B-Table 9 }
exc1-Param-T2-PLP-B-Column-10 OBJECT IDENTIFIER ::= { exc1-Param-T2-PLP-B-Table 10 }
exc1-Param-T2-PLP-B-Column-11 OBJECT IDENTIFIER ::= { exc1-Param-T2-PLP-B-Table 11 }
exc1-Param-T2-PLP-B-Column-12 OBJECT IDENTIFIER ::= { exc1-Param-T2-PLP-B-Table 12 }
exc1-Param-T2-PLP-B-Column-13 OBJECT IDENTIFIER ::= { exc1-Param-T2-PLP-B-Table 13 }
exc1-Param-T2-PLP-B-Column-14 OBJECT IDENTIFIER ::= { exc1-Param-T2-PLP-B-Table 14 }
exc1-Param-T2-PLP-B-Column-15 OBJECT IDENTIFIER ::= { exc1-Param-T2-PLP-B-Table 15 }
exc1-Param-T2-PLP-B-Column-16 OBJECT IDENTIFIER ::= { exc1-Param-T2-PLP-B-Table 16 }
exc1-Param-T2-Settings-Frame-Modulation OBJECT IDENTIFIER ::= { exc1-Param-T2-Settings 1 }
exc1-Param-T2-Settings-Frame-Structure OBJECT IDENTIFIER ::= { exc1-Param-T2-Settings 2 }
exc1-Param-T2-Settings-PAPR OBJECT IDENTIFIER ::= { exc1-Param-T2-Settings 3 }
exc1-Param-T2-Settings-Network OBJECT IDENTIFIER ::= { exc1-Param-T2-Settings 4 }
exc1-Param-T-MFN     OBJECT IDENTIFIER ::= { exc1-Param-DVB-T 1 }
exc1-Param-T-SFN     OBJECT IDENTIFIER ::= { exc1-Param-DVB-T 2 }
exc1-Param-T-Mode    OBJECT IDENTIFIER ::= { exc1-Param-DVB-T 3 }
exc1-Param-T-TPS     OBJECT IDENTIFIER ::= { exc1-Param-DVB-T 4 }
exc1-Param-T-Specific-Config OBJECT IDENTIFIER ::= { exc1-Param-DVB-T 5 }
exc1-Param-T-MIP-Control OBJECT IDENTIFIER ::= { exc1-Param-DVB-T 6 }
exc1-Param-Input-Main OBJECT IDENTIFIER ::= { exc1-Param-Input 1 }
exc1-Param-Input-Clever-Parameters OBJECT IDENTIFIER ::= { exc1-Param-Input 2 }
exc1-Param-Input-IP-1-Control OBJECT IDENTIFIER ::= { exc1-Param-Input 3 }
exc1-Param-Input-IP-2-Control OBJECT IDENTIFIER ::= { exc1-Param-Input 4 }
exc1-Param-Input-IP-1-RX OBJECT IDENTIFIER ::= { exc1-Param-Input 5 }
exc1-Param-Input-IP-2-RX OBJECT IDENTIFIER ::= { exc1-Param-Input 6 }
exc1-Param-Input-IP-1-IGMP OBJECT IDENTIFIER ::= { exc1-Param-Input 7 }
exc1-Param-Input-IP-2-IGMP OBJECT IDENTIFIER ::= { exc1-Param-Input 8 }
exc1-Param-Input-Clever-Switch-IP-Parameters OBJECT IDENTIFIER ::= { exc1-Param-Input 9 }
exc1-Param-Glonass-GPS-Monitoring OBJECT IDENTIFIER ::= { exc1-Param-Glonass-GPS 1 }
exc1-Param-Glonass-GPS-Control OBJECT IDENTIFIER ::= { exc1-Param-Glonass-GPS 2 }
exc1-Param-Mon-Main  OBJECT IDENTIFIER ::= { exc1-Param-Monitoring 1 }
exc1-Param-Mon-Stream1 OBJECT IDENTIFIER ::= { exc1-Param-Monitoring 2 }
exc1-Param-Mon-Stream2 OBJECT IDENTIFIER ::= { exc1-Param-Monitoring 3 }
exc1-Param-Mon-Clever-Status OBJECT IDENTIFIER ::= { exc1-Param-Monitoring 4 }
exc1-Param-Mon-ASI   OBJECT IDENTIFIER ::= { exc1-Param-Monitoring 5 }
exc1-Param-Mon-IP-Inputs OBJECT IDENTIFIER ::= { exc1-Param-Monitoring 6 }
exc1-Param-Mon-Clever-Switch-IP-Status OBJECT IDENTIFIER ::= { exc1-Param-Monitoring 7 }
exc1-Param-Mon-IP-Input-Status OBJECT IDENTIFIER ::= { exc1-Param-Mon-IP-Inputs 1 }
exc1-Param-Mon-IP-IP-1-Status OBJECT IDENTIFIER ::= { exc1-Param-Mon-IP-Inputs 2 }
exc1-Param-Mon-IP-IP-2-Status OBJECT IDENTIFIER ::= { exc1-Param-Mon-IP-Inputs 3 }
exc1-Param-Mon-IP-IP-1-RX-Status OBJECT IDENTIFIER ::= { exc1-Param-Mon-IP-Inputs 4 }
exc1-Param-Mon-IP-IP-2-RX-Status OBJECT IDENTIFIER ::= { exc1-Param-Mon-IP-Inputs 5 }
exc1-Param-Mon-ASI-1-Status OBJECT IDENTIFIER ::= { exc1-Param-Mon-ASI 1 }
exc1-Param-Mon-ASI-2-Status OBJECT IDENTIFIER ::= { exc1-Param-Mon-ASI 2 }
exc1-Display-Main    OBJECT IDENTIFIER ::= { exc1-Display 1 }
exc1-Aux-Connected   OBJECT IDENTIFIER ::= { exc1-Auxiliary 1 }
exc1-Aux-Processing  OBJECT IDENTIFIER ::= { exc1-Auxiliary 2 }
exc1-Aux-Values      OBJECT IDENTIFIER ::= { exc1-Auxiliary 3 }
exc1-Aux-Options     OBJECT IDENTIFIER ::= { exc1-Auxiliary 4 }
exc1-Aux-Commands    OBJECT IDENTIFIER ::= { exc1-Auxiliary 5 }
PolarisControlUnit-1 OBJECT IDENTIFIER ::= { Polaris-ControlUnits 1 }
ctl1-Unit            OBJECT IDENTIFIER ::= { PolarisControlUnit-1 1 }
ctl1-Auxiliary       OBJECT IDENTIFIER ::= { PolarisControlUnit-1 2 }
ctl1-Display         OBJECT IDENTIFIER ::= { PolarisControlUnit-1 3 }
ctl1-Controls        OBJECT IDENTIFIER ::= { PolarisControlUnit-1 4 }
ctl1-Ballast         OBJECT IDENTIFIER ::= { PolarisControlUnit-1 5 }
ctl1-Cu6             OBJECT IDENTIFIER ::= { PolarisControlUnit-1 6 }
ctl1cu6-Cu6Display   OBJECT IDENTIFIER ::= { ctl1-Cu6 1 }
ctl1cu6-Cu6Control   OBJECT IDENTIFIER ::= { ctl1-Cu6 3 }
ctl1cu6-Cu6Messages  OBJECT IDENTIFIER ::= { ctl1-Cu6 4 }
Polaris-System-Display OBJECT IDENTIFIER ::= { Polaris-System 1 }
Polaris-System-Controls OBJECT IDENTIFIER ::= { Polaris-System 2 }
Polaris-SysCtl-SNMP  OBJECT IDENTIFIER ::= { Polaris-System-Controls 1 }
Polaris-SysCtl-RCS   OBJECT IDENTIFIER ::= { Polaris-System-Controls 3 }
Polaris-SysCtl-Misc  OBJECT IDENTIFIER ::= { Polaris-System-Controls 4 }
Polaris-SysCtl-Ignore-Devices OBJECT IDENTIFIER ::= { Polaris-System-Controls 5 }
Polaris-SysCtl-sysCtl OBJECT IDENTIFIER ::= { Polaris-System-Controls 7 }
Polaris-SysCtl-SNMP-Trap-Managers OBJECT IDENTIFIER ::= { Polaris-SysCtl-SNMP 1 }
Polaris-SysCtl-SNMP-Other-Settings OBJECT IDENTIFIER ::= { Polaris-SysCtl-SNMP 2 }
Polaris-SysCtl-SNMP-Misc OBJECT IDENTIFIER ::= { Polaris-SysCtl-SNMP 3 }
Polaris-SysCtl-SNMP-Managers-IP OBJECT IDENTIFIER ::= { Polaris-SysCtl-SNMP-Trap-Managers 1 }
Polaris-SysCtl-SNMP-Managers-Port OBJECT IDENTIFIER ::= { Polaris-SysCtl-SNMP-Trap-Managers 2 }
Polaris-SysCtl-SNMP-Managers-Community OBJECT IDENTIFIER ::= { Polaris-SysCtl-SNMP-Trap-Managers 3 }
Polaris-SysCtl-SNMP-Managers-ID OBJECT IDENTIFIER ::= { Polaris-SysCtl-SNMP-Trap-Managers 4 }
Polaris-SysDisp-Main OBJECT IDENTIFIER ::= { Polaris-System-Display 1 }
Polaris-SysDisp-Powers OBJECT IDENTIFIER ::= { Polaris-System-Display 2 }
Polaris-SysDisp-Devices OBJECT IDENTIFIER ::= { Polaris-System-Display 3 }
Polaris-SysDisp-RCS  OBJECT IDENTIFIER ::= { Polaris-System-Display 4 }
Polaris-SysDisp-Pars OBJECT IDENTIFIER ::= { Polaris-System-Display 5 }
Polaris-SysDisp-Devices-Types OBJECT IDENTIFIER ::= { Polaris-System-Display 6 }
Polaris-SysDisp-SNMP OBJECT IDENTIFIER ::= { Polaris-System-Display 7 }
Polaris-SysDisp-Transmitter OBJECT IDENTIFIER ::= { Polaris-System-Display 10 }
Polaris-SysDisp-SNMP-Main OBJECT IDENTIFIER ::= { Polaris-SysDisp-SNMP 1 }
Polaris-SysDisp-SNMP-Statistics OBJECT IDENTIFIER ::= { Polaris-SysDisp-SNMP 2 }
Polaris-SysDisp-SNMP-Stat-SNMP-Informs OBJECT IDENTIFIER ::= { Polaris-SysDisp-SNMP-Statistics 1 }
Polaris-SysDisp-SNMP-Stat-Access-Errors-Counters OBJECT IDENTIFIER ::= { Polaris-SysDisp-SNMP-Statistics 2 }
Polaris-SysDisp-SNMP-Stat-SNMP-Thread-Monitoring OBJECT IDENTIFIER ::= { Polaris-SysDisp-SNMP-Statistics 3 }
Polaris-SysDisp-SNMP-Stat-SNMP-Other OBJECT IDENTIFIER ::= { Polaris-SysDisp-SNMP-Statistics 4 }
Polaris-SysDisp-SNMP-Stat-SNMP-Inf-Manager-1 OBJECT IDENTIFIER ::= { Polaris-SysDisp-SNMP-Stat-SNMP-Informs 1 }
Polaris-SysDisp-SNMP-Stat-SNMP-Inf-Manager-2 OBJECT IDENTIFIER ::= { Polaris-SysDisp-SNMP-Stat-SNMP-Informs 2 }
Polaris-SysDisp-SNMP-Stat-SNMP-Inf-Manager-3 OBJECT IDENTIFIER ::= { Polaris-SysDisp-SNMP-Stat-SNMP-Informs 3 }
Polaris-SysDisp-SNMP-Stat-SNMP-Inf-Manager-4 OBJECT IDENTIFIER ::= { Polaris-SysDisp-SNMP-Stat-SNMP-Informs 4 }
uni-System           OBJECT IDENTIFIER ::= { Polaris-UNIFIED 1 }
uni-System-Display   OBJECT IDENTIFIER ::= { uni-System 1 }
uni-System-Controls  OBJECT IDENTIFIER ::= { uni-System 2 }
uniSysCtl-SNMP       OBJECT IDENTIFIER ::= { uni-System-Controls 1 }
uniSysCtl-RCS        OBJECT IDENTIFIER ::= { uni-System-Controls 3 }
uniSysCtl-Misc       OBJECT IDENTIFIER ::= { uni-System-Controls 4 }
uniSysCtl-Ignore-Devices OBJECT IDENTIFIER ::= { uni-System-Controls 5 }
uniSysCtl-sysCtl     OBJECT IDENTIFIER ::= { uni-System-Controls 7 }
uniSysCtl-SNMP-Trap-Managers OBJECT IDENTIFIER ::= { uniSysCtl-SNMP 1 }
uniSysCtl-SNMP-Other-Settings OBJECT IDENTIFIER ::= { uniSysCtl-SNMP 2 }
uniSysCtl-SNMP-Misc  OBJECT IDENTIFIER ::= { uniSysCtl-SNMP 3 }
uniSysCtl-SNMP-Managers-IP OBJECT IDENTIFIER ::= { uniSysCtl-SNMP-Trap-Managers 1 }
uniSysCtl-SNMP-Managers-Port OBJECT IDENTIFIER ::= { uniSysCtl-SNMP-Trap-Managers 2 }
uniSysCtl-SNMP-Managers-Community OBJECT IDENTIFIER ::= { uniSysCtl-SNMP-Trap-Managers 3 }
uniSysCtl-SNMP-Managers-ID OBJECT IDENTIFIER ::= { uniSysCtl-SNMP-Trap-Managers 4 }
uniSysDisp-Main      OBJECT IDENTIFIER ::= { uni-System-Display 1 }
uniSysDisp-Powers    OBJECT IDENTIFIER ::= { uni-System-Display 2 }
uniSysDisp-Devices   OBJECT IDENTIFIER ::= { uni-System-Display 3 }
uniSysDisp-RCS       OBJECT IDENTIFIER ::= { uni-System-Display 4 }
uniSysDisp-Pars      OBJECT IDENTIFIER ::= { uni-System-Display 5 }
uniSysDisp-Devices-Types OBJECT IDENTIFIER ::= { uni-System-Display 6 }
uniSysDisp-SNMP      OBJECT IDENTIFIER ::= { uni-System-Display 7 }
uniSysDisp-Transmitter OBJECT IDENTIFIER ::= { uni-System-Display 10 }
uniSysDisp-SNMP-Main OBJECT IDENTIFIER ::= { uniSysDisp-SNMP 1 }
uniSysDisp-SNMP-Statistics OBJECT IDENTIFIER ::= { uniSysDisp-SNMP 2 }
uniSysDisp-SNMP-Stat-SNMP-Informs OBJECT IDENTIFIER ::= { uniSysDisp-SNMP-Statistics 1 }
uniSysDisp-SNMP-Stat-Access-Errors-Counters OBJECT IDENTIFIER ::= { uniSysDisp-SNMP-Statistics 2 }
uniSysDisp-SNMP-Stat-SNMP-Thread-Monitoring OBJECT IDENTIFIER ::= { uniSysDisp-SNMP-Statistics 3 }
uniSysDisp-SNMP-Stat-SNMP-Other OBJECT IDENTIFIER ::= { uniSysDisp-SNMP-Statistics 4 }
uniSysDisp-SNMP-Stat-SNMP-Inf-Manager-1 OBJECT IDENTIFIER ::= { uniSysDisp-SNMP-Stat-SNMP-Informs 1 }
uniSysDisp-SNMP-Stat-SNMP-Inf-Manager-2 OBJECT IDENTIFIER ::= { uniSysDisp-SNMP-Stat-SNMP-Informs 2 }
uniSysDisp-SNMP-Stat-SNMP-Inf-Manager-3 OBJECT IDENTIFIER ::= { uniSysDisp-SNMP-Stat-SNMP-Informs 3 }
uniSysDisp-SNMP-Stat-SNMP-Inf-Manager-4 OBJECT IDENTIFIER ::= { uniSysDisp-SNMP-Stat-SNMP-Informs 4 }

--- Edges

funCtlMisc-Min-Currents-Value OBJECT-TYPE
	SYNTAX      Integer32
	MAX-ACCESS  read-write
	STATUS      current
	DESCRIPTION
		"Minimal currents value: 0..20, unit: 1 % / 0.1 A"
        ::= { funCtl-Misc 1 }

funCtlMisc-Weak-Exciters-Auto-Switching OBJECT-TYPE
	SYNTAX      Integer32
	MAX-ACCESS  read-only
	STATUS      current
	DESCRIPTION
		"Weak exciters autoswitching (-1 = unused)"
        ::= { funCtl-Misc 2 }

funCtlMisc-Ballast-Overheat-Temp OBJECT-TYPE
	SYNTAX      Integer32
	MAX-ACCESS  read-only
	STATUS      current
	DESCRIPTION
		"Ballasts overheat temperature: 0..80 (-1 = unused)"
        ::= { funCtl-Misc 3 }

funCtlMisc-Amplifier-Overheat-Temp OBJECT-TYPE
	SYNTAX      Integer32
	MAX-ACCESS  read-only
	STATUS      current
	DESCRIPTION
		"Amplifiers overheat temperature: 0..80 (-1 = unused)"
        ::= { funCtl-Misc 4 }

funCtlMisc-Hide-Inactive-ASI OBJECT-TYPE
	SYNTAX      Integer32
	MAX-ACCESS  read-only
	STATUS      current
	DESCRIPTION
		"Hide ASI inputs status/alarms for inactive exciter (-1 = unused)"
        ::= { funCtl-Misc 5 }

funCtlMisc-Amplifier-Rated-Power OBJECT-TYPE
	SYNTAX      Integer32
	MAX-ACCESS  read-write
	STATUS      current
	DESCRIPTION
		"Amplifier rated power (-1 = unused, 0 = not selected, 1 = standard, 2 = special)"
        ::= { funCtl-Misc 6 }

funCtlMisc-Exc-Alarms-Mask OBJECT-TYPE
	SYNTAX      Integer32
	MAX-ACCESS  read-only
	STATUS      current
	DESCRIPTION
		"-1 = unused"
        ::= { funCtl-Misc 7 }

funCtlPwrMon-Alert-Type OBJECT-TYPE
	SYNTAX      INTEGER {unknown (0), warning (1), failure (2)}
	MAX-ACCESS  read-write
	STATUS      current
	DESCRIPTION
		""
        ::= { funCtl-PowerOut-Monitor 1 }

funCtlPwrMon-Critical-Type OBJECT-TYPE
	SYNTAX      INTEGER {no (0), yes (1)}
	MAX-ACCESS  read-write
	STATUS      current
	DESCRIPTION
		""
        ::= { funCtl-PowerOut-Monitor 2 }

funCtlPwrMon-PowerOut-Min OBJECT-TYPE
	SYNTAX      Integer32
	MAX-ACCESS  read-write
	STATUS      current
	DESCRIPTION
		""
        ::= { funCtl-PowerOut-Monitor 3 }

funCtlPwrMon-PowerOut-Max OBJECT-TYPE
	SYNTAX      Integer32
	MAX-ACCESS  read-write
	STATUS      current
	DESCRIPTION
		""
        ::= { funCtl-PowerOut-Monitor 4 }

funCtlPwrMon-Alert-Delay OBJECT-TYPE
	SYNTAX      Integer32
	MAX-ACCESS  read-write
	STATUS      current
	DESCRIPTION
		""
        ::= { funCtl-PowerOut-Monitor 5 }

funCtlPwrMon-Alert-Activate-Delay OBJECT-TYPE
	SYNTAX      Integer32
	MAX-ACCESS  read-only
	STATUS      current
	DESCRIPTION
		""
        ::= { funCtl-PowerOut-Monitor 6 }

funDispPwrMon-PowerOut-Value OBJECT-TYPE
	SYNTAX      Integer32
	MAX-ACCESS  read-only
	STATUS      current
	DESCRIPTION
		""
        ::= { funDisp-PowerOutMonitor 1 }

funDispPwrMon-PowerOut-Max OBJECT-TYPE
	SYNTAX      Integer32
	MAX-ACCESS  read-only
	STATUS      current
	DESCRIPTION
		""
        ::= { funDisp-PowerOutMonitor 2 }

funDispPwrMon-Timer OBJECT-TYPE
	SYNTAX      Integer32
	MAX-ACCESS  read-only
	STATUS      current
	DESCRIPTION
		""
        ::= { funDisp-PowerOutMonitor 3 }

funDispMain-Status  OBJECT-TYPE
	SYNTAX      INTEGER {oK (0), warning (1), failure (2), warningAndFailure (3)}
	MAX-ACCESS  read-only
	STATUS      current
	DESCRIPTION
		""
        ::= { funDisp-Main 1 }

funDispMain-Status-Info OBJECT-TYPE
	SYNTAX      OCTET STRING
	MAX-ACCESS  read-only
	STATUS      current
	DESCRIPTION
		""
        ::= { funDisp-Main 2 }

funDispMain-Status-Warning OBJECT-TYPE
	SYNTAX      OCTET STRING
	MAX-ACCESS  read-only
	STATUS      current
	DESCRIPTION
		""
        ::= { funDisp-Main 3 }

funDispMain-Status-Failure OBJECT-TYPE
	SYNTAX      OCTET STRING
	MAX-ACCESS  read-only
	STATUS      current
	DESCRIPTION
		""
        ::= { funDisp-Main 4 }

ssm1Ctl-ResetController OBJECT-TYPE
	SYNTAX      Integer32
	MAX-ACCESS  read-write
	STATUS      current
	DESCRIPTION
		"Set 1 to reset controller"
        ::= { ssm1-Control 1 }

ssm1Ctl-Serial      OBJECT-TYPE
	SYNTAX      Integer32
	MAX-ACCESS  read-write
	STATUS      current
	DESCRIPTION
		""
        ::= { ssm1-Control 2 }

ssm1Ctl-SwitchReserve OBJECT-TYPE
	SYNTAX      INTEGER {bothAntenna (0), reserve_A (1), reserve_B (2)}
	MAX-ACCESS  read-write
	STATUS      current
	DESCRIPTION
		""
        ::= { ssm1-Control 3 }

ssm1Ctl-MuteOutputA OBJECT-TYPE
	SYNTAX      INTEGER {unlock (0), lock (1)}
	MAX-ACCESS  read-write
	STATUS      current
	DESCRIPTION
		""
        ::= { ssm1-Control 4 }

ssm1Ctl-MuteOutputB OBJECT-TYPE
	SYNTAX      INTEGER {unlock (0), lock (1)}
	MAX-ACCESS  read-write
	STATUS      current
	DESCRIPTION
		""
        ::= { ssm1-Control 5 }

ssm1Ctl-MuteOutputE OBJECT-TYPE
	SYNTAX      INTEGER {unlock (0), lock (1)}
	MAX-ACCESS  read-write
	STATUS      current
	DESCRIPTION
		""
        ::= { ssm1-Control 6 }

ssm1Ctl-AutoSwitchOn OBJECT-TYPE
	SYNTAX      INTEGER {off (0), on (1)}
	MAX-ACCESS  read-write
	STATUS      current
	DESCRIPTION
		""
        ::= { ssm1-Control 7 }

ssm1Ctl-AutoSwitchPriority OBJECT-TYPE
	SYNTAX      INTEGER {none (0), transmitterA (1), transmitterB (2)}
	MAX-ACCESS  read-write
	STATUS      current
	DESCRIPTION
		""
        ::= { ssm1-Control 8 }

ssm1Ctl-AutoSwitchTimeout OBJECT-TYPE
	SYNTAX      Integer32
	MAX-ACCESS  read-write
	STATUS      current
	DESCRIPTION
		"Delay in seconds before switch A/B transmitter to reserve "
        ::= { ssm1-Control 9 }

ssm1Ctl-ResetEvents OBJECT-TYPE
	SYNTAX      Integer32
	MAX-ACCESS  read-write
	STATUS      current
	DESCRIPTION
		"set 1 to reset active events "
        ::= { ssm1-Control 10 }

ssm1Ctl-MaxAutoSwitchRetries OBJECT-TYPE
	SYNTAX      Integer32
	MAX-ACCESS  read-write
	STATUS      current
	DESCRIPTION
		"Maximum retries of auto switch process 1..15 "
        ::= { ssm1-Control 11 }

ssm1Ctl-CoolReserve OBJECT-TYPE
	SYNTAX      INTEGER {off (0), on (1)}
	MAX-ACCESS  read-write
	STATUS      current
	DESCRIPTION
		"set 1 to disable the liquid cooling if transmitter R is in standby mode"
        ::= { ssm1-Control 12 }

ssm1Ctl-TransmitterR_Channel OBJECT-TYPE
	SYNTAX      INTEGER {a (0), b (1)}
	MAX-ACCESS  read-write
	STATUS      current
	DESCRIPTION
		"Transmitter's R channel for operation in standby mode"
        ::= { ssm1-Control 13 }

ssm1Ctl-MuteTransmitterRAtSysLoadWorking OBJECT-TYPE
	SYNTAX      INTEGER {unlock (0), lock (1)}
	MAX-ACCESS  read-write
	STATUS      current
	DESCRIPTION
		""
        ::= { ssm1-Control 14 }

ssm1Ctl-AutoSwitchOnlyPriorityTransmitter OBJECT-TYPE
	SYNTAX      Integer32
	MAX-ACCESS  read-write
	STATUS      current
	DESCRIPTION
		"Replace the priority transmitter by reserve only 1 - on, 0 - off"
        ::= { ssm1-Control 15 }

ssm1Ctl-SendStartCmdToLcs OBJECT-TYPE
	SYNTAX      INTEGER {false(0), true(1)}
	MAX-ACCESS  read-write
	STATUS      current
	DESCRIPTION
		""
        ::= { ssm1-Control 16 }

ssm1Ctl-LcsAgentPort OBJECT-TYPE
	SYNTAX      Integer32
	MAX-ACCESS  read-write
	STATUS      current
	DESCRIPTION
		""
        ::= { ssm1-Control 17 }

ssm1Ctl-MuteOnFiltersCoolingAlarm OBJECT-TYPE
	SYNTAX      INTEGER {unlock (0), lock (1)}
	MAX-ACCESS  read-write
	STATUS      current
	DESCRIPTION
		"Mute transmitters in case of filters cooling alarm"
        ::= { ssm1-Control 18 }

ssm1TranR-MuteDevicePosition OBJECT-TYPE
	SYNTAX      INTEGER {unknown (0), noMuting (1), muting (2)}
	MAX-ACCESS  read-only
	STATUS      current
	DESCRIPTION
		""
        ::= { ssm1-TransmitterR 1 }

ssm1TranR-MuteReason OBJECT-TYPE
	SYNTAX      INTEGER {none (0), muteOutput (1), userRequest (2), switchError (4), extSensors (8)}
	MAX-ACCESS  read-only
	STATUS      current
	DESCRIPTION
		""
        ::= { ssm1-TransmitterR 2 }

ssm1TranR-Power-Out OBJECT-TYPE
	SYNTAX      Integer32
	MAX-ACCESS  read-only
	STATUS      current
	DESCRIPTION
		""
        ::= { ssm1-TransmitterR 3 }

ssm1TranR-Load      OBJECT-TYPE
	SYNTAX      INTEGER {unknown (0), outputA (1), outputB (2), equivalent (3)}
	MAX-ACCESS  read-only
	STATUS      current
	DESCRIPTION
		""
        ::= { ssm1-TransmitterR 4 }

ssm1TranR-IsMuted   OBJECT-TYPE
	SYNTAX      INTEGER {false(0), true(1)}
	MAX-ACCESS  read-only
	STATUS      current
	DESCRIPTION
		""
        ::= { ssm1-TransmitterR 5 }

ssm1TranR-AdcStatus OBJECT-TYPE
	SYNTAX      INTEGER {normal (0), overload (1)}
	MAX-ACCESS  read-only
	STATUS      current
	DESCRIPTION
		"ADC Status: Overload(1) - Data not valid"
        ::= { ssm1-TransmitterR 6 }

ssm1TranR-MuteDeviceState OBJECT-TYPE
	SYNTAX      INTEGER {normal (0), failure (1), noConnection (2)}
	MAX-ACCESS  read-only
	STATUS      current
	DESCRIPTION
		""
        ::= { ssm1-TransmitterR 7 }

ssm1TranB-MuteDevicePosition OBJECT-TYPE
	SYNTAX      INTEGER {unknown (0), noMuting (1), muting (2)}
	MAX-ACCESS  read-only
	STATUS      current
	DESCRIPTION
		""
        ::= { ssm1-TransmitterB 1 }

ssm1TranB-MuteReason OBJECT-TYPE
	SYNTAX      INTEGER {none (0), muteOutput (1), userRequest (2), switchError (4), extSensors (8)}
	MAX-ACCESS  read-only
	STATUS      current
	DESCRIPTION
		""
        ::= { ssm1-TransmitterB 2 }

ssm1TranB-Power-Out OBJECT-TYPE
	SYNTAX      Integer32
	MAX-ACCESS  read-only
	STATUS      current
	DESCRIPTION
		""
        ::= { ssm1-TransmitterB 3 }

ssm1TranB-Load      OBJECT-TYPE
	SYNTAX      INTEGER {unknown (0), outputA (1), outputB (2), equivalent (3)}
	MAX-ACCESS  read-only
	STATUS      current
	DESCRIPTION
		""
        ::= { ssm1-TransmitterB 4 }

ssm1TranB-IsMuted   OBJECT-TYPE
	SYNTAX      INTEGER {false(0), true(1)}
	MAX-ACCESS  read-only
	STATUS      current
	DESCRIPTION
		""
        ::= { ssm1-TransmitterB 5 }

ssm1TranB-AdcStatus OBJECT-TYPE
	SYNTAX      INTEGER {normal (0), overload (1)}
	MAX-ACCESS  read-only
	STATUS      current
	DESCRIPTION
		"ADC Status: Overload(1) - Data not valid"
        ::= { ssm1-TransmitterB 6 }

ssm1TranB-MuteDeviceState OBJECT-TYPE
	SYNTAX      INTEGER {normal (0), failure (1), noConnection (2)}
	MAX-ACCESS  read-only
	STATUS      current
	DESCRIPTION
		""
        ::= { ssm1-TransmitterB 7 }

ssm1TranB-MuteTransmitterStatusB OBJECT-TYPE
	SYNTAX      INTEGER {unlock (0), lock (1)}
	MAX-ACCESS  read-only
	STATUS      current
	DESCRIPTION
		""
        ::= { ssm1-TransmitterB 8 }

ssm1TranA-MuteDevicePosition OBJECT-TYPE
	SYNTAX      INTEGER {unknown (0), noMuting (1), muting (2)}
	MAX-ACCESS  read-only
	STATUS      current
	DESCRIPTION
		""
        ::= { ssm1-TransmitterA 1 }

ssm1TranA-MuteReason OBJECT-TYPE
	SYNTAX      INTEGER {none (0), muteOutput (1), userRequest (2), switchError (4), extSensors (8)}
	MAX-ACCESS  read-only
	STATUS      current
	DESCRIPTION
		""
        ::= { ssm1-TransmitterA 2 }

ssm1TranA-Power-Out OBJECT-TYPE
	SYNTAX      Integer32
	MAX-ACCESS  read-only
	STATUS      current
	DESCRIPTION
		""
        ::= { ssm1-TransmitterA 3 }

ssm1TranA-Load      OBJECT-TYPE
	SYNTAX      INTEGER {unknown (0), outputA (1), outputB (2), equivalent (3)}
	MAX-ACCESS  read-only
	STATUS      current
	DESCRIPTION
		""
        ::= { ssm1-TransmitterA 4 }

ssm1TranA-IsMuted   OBJECT-TYPE
	SYNTAX      INTEGER {false(0), true(1)}
	MAX-ACCESS  read-only
	STATUS      current
	DESCRIPTION
		""
        ::= { ssm1-TransmitterA 5 }

ssm1TranA-AdcStatus OBJECT-TYPE
	SYNTAX      INTEGER {normal (0), overload (1)}
	MAX-ACCESS  read-only
	STATUS      current
	DESCRIPTION
		"ADC Status: Overload(1) - Data not valid"
        ::= { ssm1-TransmitterA 6 }

ssm1TranA-MuteDeviceState OBJECT-TYPE
	SYNTAX      INTEGER {normal (0), failure (1), noConnection (2)}
	MAX-ACCESS  read-only
	STATUS      current
	DESCRIPTION
		""
        ::= { ssm1-TransmitterA 7 }

ssm1TranA-MuteTransmitterStatusA OBJECT-TYPE
	SYNTAX      INTEGER {unlock (0), lock (1)}
	MAX-ACCESS  read-only
	STATUS      current
	DESCRIPTION
		""
        ::= { ssm1-TransmitterA 8 }

ssm1Out-OutputA-Power OBJECT-TYPE
	SYNTAX      Integer32
	MAX-ACCESS  read-only
	STATUS      current
	DESCRIPTION
		""
        ::= { ssm1-Output 1 }

ssm1Out-OutputB-Power OBJECT-TYPE
	SYNTAX      Integer32
	MAX-ACCESS  read-only
	STATUS      current
	DESCRIPTION
		""
        ::= { ssm1-Output 2 }

ssm1Out-OutputE-Power OBJECT-TYPE
	SYNTAX      Integer32
	MAX-ACCESS  read-only
	STATUS      current
	DESCRIPTION
		""
        ::= { ssm1-Output 3 }

ssm1Out-OutputA-Source OBJECT-TYPE
	SYNTAX      INTEGER {unknown (0), transmitterA (1), transmitterB (2), transmitterR (3)}
	MAX-ACCESS  read-only
	STATUS      current
	DESCRIPTION
		""
        ::= { ssm1-Output 4 }

ssm1Out-OutputB-Source OBJECT-TYPE
	SYNTAX      INTEGER {unknown (0), transmitterA (1), transmitterB (2), transmitterR (3)}
	MAX-ACCESS  read-only
	STATUS      current
	DESCRIPTION
		""
        ::= { ssm1-Output 5 }

ssm1Out-OutputE-Source OBJECT-TYPE
	SYNTAX      INTEGER {unknown (0), transmitterA (1), transmitterB (2), transmitterR (3)}
	MAX-ACCESS  read-only
	STATUS      current
	DESCRIPTION
		""
        ::= { ssm1-Output 6 }

ssm1Out-TransmitterA-SwitchAllow OBJECT-TYPE
	SYNTAX      INTEGER {notAllowed (0), allowed (1)}
	MAX-ACCESS  read-only
	STATUS      current
	DESCRIPTION
		"Allow switch transmitter A to reserve"
        ::= { ssm1-Output 7 }

ssm1Out-TransmitterB-SwitchAllow OBJECT-TYPE
	SYNTAX      INTEGER {notAllowed (0), allowed (1)}
	MAX-ACCESS  read-only
	STATUS      current
	DESCRIPTION
		"Allow switch transmitter B to reserve"
        ::= { ssm1-Output 8 }

ssm1Out-TransmitterR-SwitchAllow OBJECT-TYPE
	SYNTAX      INTEGER {notAllowed (0), allowed (1)}
	MAX-ACCESS  read-only
	STATUS      current
	DESCRIPTION
		"Allow switch transmitter R to reserve"
        ::= { ssm1-Output 9 }

ssm1Out-Is-Out-A-Power-Visible OBJECT-TYPE
	SYNTAX      INTEGER {notVisible (0), visible (1)}
	MAX-ACCESS  read-only
	STATUS      current
	DESCRIPTION
		""
        ::= { ssm1-Output 10 }

ssm1Out-Is-Out-B-Power-Visible OBJECT-TYPE
	SYNTAX      INTEGER {notVisible (0), visible (1)}
	MAX-ACCESS  read-only
	STATUS      current
	DESCRIPTION
		""
        ::= { ssm1-Output 11 }

ssm1Out-Is-Out-E-Power-Visible OBJECT-TYPE
	SYNTAX      INTEGER {notVisible (0), visible (1)}
	MAX-ACCESS  read-only
	STATUS      current
	DESCRIPTION
		""
        ::= { ssm1-Output 12 }

ssm1Disp-Status-Info OBJECT-TYPE
	SYNTAX      OCTET STRING
	MAX-ACCESS  read-only
	STATUS      current
	DESCRIPTION
		""
        ::= { ssm1-Display 1 }

ssm1Disp-Status-Warning OBJECT-TYPE
	SYNTAX      OCTET STRING
	MAX-ACCESS  read-only
	STATUS      current
	DESCRIPTION
		""
        ::= { ssm1-Display 2 }

ssm1Disp-Status-Failure OBJECT-TYPE
	SYNTAX      OCTET STRING
	MAX-ACCESS  read-only
	STATUS      current
	DESCRIPTION
		""
        ::= { ssm1-Display 3 }

ssm1Disp-HardwareVersion OBJECT-TYPE
	SYNTAX      OCTET STRING
	MAX-ACCESS  read-only
	STATUS      current
	DESCRIPTION
		""
        ::= { ssm1-Display 4 }

ssm1Disp-SoftwareVersion OBJECT-TYPE
	SYNTAX      OCTET STRING
	MAX-ACCESS  read-only
	STATUS      current
	DESCRIPTION
		""
        ::= { ssm1-Display 5 }

ssm1Disp-SwitchPositionA OBJECT-TYPE
	SYNTAX      INTEGER {unknown (0), positionAB (1), positionR (2)}
	MAX-ACCESS  read-only
	STATUS      current
	DESCRIPTION
		""
        ::= { ssm1-Display 6 }

ssm1Disp-SwitchPositionB OBJECT-TYPE
	SYNTAX      INTEGER {unknown (0), positionAB (1), positionR (2)}
	MAX-ACCESS  read-only
	STATUS      current
	DESCRIPTION
		""
        ::= { ssm1-Display 7 }

ssm1Disp-SwitchStateA OBJECT-TYPE
	SYNTAX      INTEGER {normal (0), switchProcessing (1), failure (2), noConnection (3), hanged (4)}
	MAX-ACCESS  read-only
	STATUS      current
	DESCRIPTION
		""
        ::= { ssm1-Display 8 }

ssm1Disp-SwitchStateB OBJECT-TYPE
	SYNTAX      INTEGER {normal (0), switchProcessing (1), failure (2), noConnection (3), hanged (4)}
	MAX-ACCESS  read-only
	STATUS      current
	DESCRIPTION
		""
        ::= { ssm1-Display 9 }

ssm1Disp-TransmitterA-Channel OBJECT-TYPE
	SYNTAX      Integer32
	MAX-ACCESS  read-only
	STATUS      current
	DESCRIPTION
		""
        ::= { ssm1-Display 10 }

ssm1Disp-TransmitterB-Channel OBJECT-TYPE
	SYNTAX      Integer32
	MAX-ACCESS  read-only
	STATUS      current
	DESCRIPTION
		""
        ::= { ssm1-Display 11 }

ssm1Disp-TransmitterR-Channel OBJECT-TYPE
	SYNTAX      Integer32
	MAX-ACCESS  read-only
	STATUS      current
	DESCRIPTION
		""
        ::= { ssm1-Display 12 }

ssm1Disp-IsSwitchAllowed OBJECT-TYPE
	SYNTAX      INTEGER {false(0), true(1)}
	MAX-ACCESS  read-only
	STATUS      current
	DESCRIPTION
		""
        ::= { ssm1-Display 13 }

ssm1Disp-RetriesCounter OBJECT-TYPE
	SYNTAX      Integer32
	MAX-ACCESS  read-only
	STATUS      current
	DESCRIPTION
		"The quantity of auto switching retries"
        ::= { ssm1-Display 14 }

ssm1Aux-Divider     OBJECT-TYPE
	SYNTAX      Integer32
	MAX-ACCESS  read-only
	STATUS      current
	DESCRIPTION
		""
        ::= { ssm1-Auxiliary 1 }

ssm1Aux-Units       OBJECT-TYPE
	SYNTAX      INTEGER {watt (0), kiloWatt (1), percent (2)}
	MAX-ACCESS  read-only
	STATUS      current
	DESCRIPTION
		""
        ::= { ssm1-Auxiliary 2 }

ssm1Unit-Connected  OBJECT-TYPE
	SYNTAX      INTEGER {false(0), true(1)}
	MAX-ACCESS  read-only
	STATUS      current
	DESCRIPTION
		""
        ::= { ssm1-Unit 1 }

ssm1Unit-Warning    OBJECT-TYPE
	SYNTAX      INTEGER {false(0), true(1)}
	MAX-ACCESS  read-only
	STATUS      current
	DESCRIPTION
		""
        ::= { ssm1-Unit 2 }

ssm1Unit-Failure    OBJECT-TYPE
	SYNTAX      INTEGER {false(0), true(1)}
	MAX-ACCESS  read-only
	STATUS      current
	DESCRIPTION
		""
        ::= { ssm1-Unit 3 }

ssm1Unit-Busy-Count OBJECT-TYPE
	SYNTAX      Integer32
	MAX-ACCESS  read-only
	STATUS      current
	DESCRIPTION
		""
        ::= { ssm1-Unit 4 }

ssm1Unit-Model-Version OBJECT-TYPE
	SYNTAX      OCTET STRING
	MAX-ACCESS  read-only
	STATUS      current
	DESCRIPTION
		""
        ::= { ssm1-Unit 5 }

ssm1Unit-Serial-Number OBJECT-TYPE
	SYNTAX      Integer32
	MAX-ACCESS  read-only
	STATUS      current
	DESCRIPTION
		""
        ::= { ssm1-Unit 6 }

ssm1Unit-Firmware-Version OBJECT-TYPE
	SYNTAX      OCTET STRING
	MAX-ACCESS  read-only
	STATUS      current
	DESCRIPTION
		"Major.Minor.Release (H:M:S) Build"
        ::= { ssm1-Unit 7 }

ssm1Unit-Dummy-8    OBJECT-TYPE
	SYNTAX      Integer32
	MAX-ACCESS  read-only
	STATUS      current
	DESCRIPTION
		""
        ::= { ssm1-Unit 8 }

ssm1Unit-Dummy-9    OBJECT-TYPE
	SYNTAX      Integer32
	MAX-ACCESS  read-only
	STATUS      current
	DESCRIPTION
		""
        ::= { ssm1-Unit 9 }

ssm1Unit-IP-Address OBJECT-TYPE
	SYNTAX      IPAddress
	MAX-ACCESS  read-only
	STATUS      current
	DESCRIPTION
		""
        ::= { ssm1-Unit 10 }

ssm1Unit-TCP-Port   OBJECT-TYPE
	SYNTAX      Integer32
	MAX-ACCESS  read-only
	STATUS      current
	DESCRIPTION
		""
        ::= { ssm1-Unit 11 }

ssm1Unit-Adapter    OBJECT-TYPE
	SYNTAX      OCTET STRING
	MAX-ACCESS  read-only
	STATUS      current
	DESCRIPTION
		""
        ::= { ssm1-Unit 12 }

ssm1Unit-Reconnects OBJECT-TYPE
	SYNTAX      Integer32
	MAX-ACCESS  read-only
	STATUS      current
	DESCRIPTION
		""
        ::= { ssm1-Unit 13 }

amp8DispCurs-Div-Current-Divider-1 OBJECT-TYPE
	SYNTAX      Integer32
	MAX-ACCESS  read-only
	STATUS      current
	DESCRIPTION
		""
        ::= { amp8Disp-Currents-Dividers 1 }

amp8DispCurs-Div-Current-Divider-2 OBJECT-TYPE
	SYNTAX      Integer32
	MAX-ACCESS  read-only
	STATUS      current
	DESCRIPTION
		""
        ::= { amp8Disp-Currents-Dividers 2 }

amp8DispCurs-Div-Current-Divider-3 OBJECT-TYPE
	SYNTAX      Integer32
	MAX-ACCESS  read-only
	STATUS      current
	DESCRIPTION
		""
        ::= { amp8Disp-Currents-Dividers 3 }

amp8DispCurs-Div-Current-Divider-4 OBJECT-TYPE
	SYNTAX      Integer32
	MAX-ACCESS  read-only
	STATUS      current
	DESCRIPTION
		""
        ::= { amp8Disp-Currents-Dividers 4 }

amp8DispCurs-Div-Current-Divider-5 OBJECT-TYPE
	SYNTAX      Integer32
	MAX-ACCESS  read-only
	STATUS      current
	DESCRIPTION
		""
        ::= { amp8Disp-Currents-Dividers 5 }

amp8DispCurs-Div-Current-Divider-6 OBJECT-TYPE
	SYNTAX      Integer32
	MAX-ACCESS  read-only
	STATUS      current
	DESCRIPTION
		""
        ::= { amp8Disp-Currents-Dividers 6 }

amp8DispCurs-Div-Current-Divider-7 OBJECT-TYPE
	SYNTAX      Integer32
	MAX-ACCESS  read-only
	STATUS      current
	DESCRIPTION
		""
        ::= { amp8Disp-Currents-Dividers 7 }

amp8DispCurs-Div-Current-Divider-8 OBJECT-TYPE
	SYNTAX      Integer32
	MAX-ACCESS  read-only
	STATUS      current
	DESCRIPTION
		""
        ::= { amp8Disp-Currents-Dividers 8 }

amp8DispCurs-Div-Current-Divider-9 OBJECT-TYPE
	SYNTAX      Integer32
	MAX-ACCESS  read-only
	STATUS      current
	DESCRIPTION
		""
        ::= { amp8Disp-Currents-Dividers 9 }

amp8DispCurs-Div-Current-Divider-10 OBJECT-TYPE
	SYNTAX      Integer32
	MAX-ACCESS  read-only
	STATUS      current
	DESCRIPTION
		""
        ::= { amp8Disp-Currents-Dividers 10 }

amp8DispCurs-Div-Current-Divider-11 OBJECT-TYPE
	SYNTAX      Integer32
	MAX-ACCESS  read-only
	STATUS      current
	DESCRIPTION
		""
        ::= { amp8Disp-Currents-Dividers 11 }

amp8DispCurs-Div-Current-Divider-12 OBJECT-TYPE
	SYNTAX      Integer32
	MAX-ACCESS  read-only
	STATUS      current
	DESCRIPTION
		""
        ::= { amp8Disp-Currents-Dividers 12 }

amp8DispCurs-Div-Current-Divider-13 OBJECT-TYPE
	SYNTAX      Integer32
	MAX-ACCESS  read-only
	STATUS      current
	DESCRIPTION
		""
        ::= { amp8Disp-Currents-Dividers 13 }

amp8DispCurs-Div-Current-Divider-14 OBJECT-TYPE
	SYNTAX      Integer32
	MAX-ACCESS  read-only
	STATUS      current
	DESCRIPTION
		""
        ::= { amp8Disp-Currents-Dividers 14 }

amp8DispCurs-Div-Current-Divider-15 OBJECT-TYPE
	SYNTAX      Integer32
	MAX-ACCESS  read-only
	STATUS      current
	DESCRIPTION
		""
        ::= { amp8Disp-Currents-Dividers 15 }

amp8DispCurs-Div-Current-Divider-16 OBJECT-TYPE
	SYNTAX      Integer32
	MAX-ACCESS  read-only
	STATUS      current
	DESCRIPTION
		""
        ::= { amp8Disp-Currents-Dividers 16 }

amp8DispCurs-Div-Current-Divider-17 OBJECT-TYPE
	SYNTAX      Integer32
	MAX-ACCESS  read-only
	STATUS      current
	DESCRIPTION
		""
        ::= { amp8Disp-Currents-Dividers 17 }

amp8DispCurs-Div-Current-Divider-18 OBJECT-TYPE
	SYNTAX      Integer32
	MAX-ACCESS  read-only
	STATUS      current
	DESCRIPTION
		""
        ::= { amp8Disp-Currents-Dividers 18 }

amp8DispCurs-Div-Current-Divider-19 OBJECT-TYPE
	SYNTAX      Integer32
	MAX-ACCESS  read-only
	STATUS      current
	DESCRIPTION
		""
        ::= { amp8Disp-Currents-Dividers 19 }

amp8DispCurs-Current-1 OBJECT-TYPE
	SYNTAX      Integer32
	MAX-ACCESS  read-only
	STATUS      current
	DESCRIPTION
		""
        ::= { amp8Disp-Currents 1 }

amp8DispCurs-Current-2 OBJECT-TYPE
	SYNTAX      Integer32
	MAX-ACCESS  read-only
	STATUS      current
	DESCRIPTION
		""
        ::= { amp8Disp-Currents 2 }

amp8DispCurs-Current-3 OBJECT-TYPE
	SYNTAX      Integer32
	MAX-ACCESS  read-only
	STATUS      current
	DESCRIPTION
		""
        ::= { amp8Disp-Currents 3 }

amp8DispCurs-Current-4 OBJECT-TYPE
	SYNTAX      Integer32
	MAX-ACCESS  read-only
	STATUS      current
	DESCRIPTION
		""
        ::= { amp8Disp-Currents 4 }

amp8DispCurs-Current-5 OBJECT-TYPE
	SYNTAX      Integer32
	MAX-ACCESS  read-only
	STATUS      current
	DESCRIPTION
		""
        ::= { amp8Disp-Currents 5 }

amp8DispCurs-Current-6 OBJECT-TYPE
	SYNTAX      Integer32
	MAX-ACCESS  read-only
	STATUS      current
	DESCRIPTION
		""
        ::= { amp8Disp-Currents 6 }

amp8DispCurs-Current-7 OBJECT-TYPE
	SYNTAX      Integer32
	MAX-ACCESS  read-only
	STATUS      current
	DESCRIPTION
		""
        ::= { amp8Disp-Currents 7 }

amp8DispCurs-Current-8 OBJECT-TYPE
	SYNTAX      Integer32
	MAX-ACCESS  read-only
	STATUS      current
	DESCRIPTION
		""
        ::= { amp8Disp-Currents 8 }

amp8DispCurs-Current-9 OBJECT-TYPE
	SYNTAX      Integer32
	MAX-ACCESS  read-only
	STATUS      current
	DESCRIPTION
		""
        ::= { amp8Disp-Currents 9 }

amp8DispCurs-Current-10 OBJECT-TYPE
	SYNTAX      Integer32
	MAX-ACCESS  read-only
	STATUS      current
	DESCRIPTION
		""
        ::= { amp8Disp-Currents 10 }

amp8DispCurs-Current-11 OBJECT-TYPE
	SYNTAX      Integer32
	MAX-ACCESS  read-only
	STATUS      current
	DESCRIPTION
		""
        ::= { amp8Disp-Currents 11 }

amp8DispCurs-Current-12 OBJECT-TYPE
	SYNTAX      Integer32
	MAX-ACCESS  read-only
	STATUS      current
	DESCRIPTION
		""
        ::= { amp8Disp-Currents 12 }

amp8DispCurs-Current-13 OBJECT-TYPE
	SYNTAX      Integer32
	MAX-ACCESS  read-only
	STATUS      current
	DESCRIPTION
		""
        ::= { amp8Disp-Currents 13 }

amp8DispCurs-Current-14 OBJECT-TYPE
	SYNTAX      Integer32
	MAX-ACCESS  read-only
	STATUS      current
	DESCRIPTION
		""
        ::= { amp8Disp-Currents 14 }

amp8DispCurs-Current-15 OBJECT-TYPE
	SYNTAX      Integer32
	MAX-ACCESS  read-only
	STATUS      current
	DESCRIPTION
		""
        ::= { amp8Disp-Currents 15 }

amp8DispCurs-Current-16 OBJECT-TYPE
	SYNTAX      Integer32
	MAX-ACCESS  read-only
	STATUS      current
	DESCRIPTION
		""
        ::= { amp8Disp-Currents 16 }

amp8DispCurs-Current-17 OBJECT-TYPE
	SYNTAX      Integer32
	MAX-ACCESS  read-only
	STATUS      current
	DESCRIPTION
		""
        ::= { amp8Disp-Currents 17 }

amp8DispCurs-Current-18 OBJECT-TYPE
	SYNTAX      Integer32
	MAX-ACCESS  read-only
	STATUS      current
	DESCRIPTION
		""
        ::= { amp8Disp-Currents 18 }

amp8DispCurs-Current-19 OBJECT-TYPE
	SYNTAX      Integer32
	MAX-ACCESS  read-only
	STATUS      current
	DESCRIPTION
		""
        ::= { amp8Disp-Currents 19 }

amp8DispTemps-Temperature-1 OBJECT-TYPE
	SYNTAX      Integer32
	MAX-ACCESS  read-only
	STATUS      current
	DESCRIPTION
		""
        ::= { amp8Disp-Temperatures 1 }

amp8DispTemps-Temperature-2 OBJECT-TYPE
	SYNTAX      Integer32
	MAX-ACCESS  read-only
	STATUS      current
	DESCRIPTION
		""
        ::= { amp8Disp-Temperatures 2 }

amp8DispMain-Status-Info OBJECT-TYPE
	SYNTAX      OCTET STRING
	MAX-ACCESS  read-only
	STATUS      current
	DESCRIPTION
		"Multiline, UTF8, separator: CRLF"
        ::= { amp8Disp-Main 1 }

amp8DispMain-Status-Warning OBJECT-TYPE
	SYNTAX      OCTET STRING
	MAX-ACCESS  read-only
	STATUS      current
	DESCRIPTION
		"Multiline, UTF8, separator: CRLF"
        ::= { amp8Disp-Main 2 }

amp8DispMain-Status-Failure OBJECT-TYPE
	SYNTAX      OCTET STRING
	MAX-ACCESS  read-only
	STATUS      current
	DESCRIPTION
		"Multiline, UTF8, separator: CRLF"
        ::= { amp8Disp-Main 3 }

amp8DispMain-Power-Out OBJECT-TYPE
	SYNTAX      Integer32
	MAX-ACCESS  read-only
	STATUS      current
	DESCRIPTION
		"Pout, unit: 0.1 W / 0.1 dB"
        ::= { amp8Disp-Main 4 }

amp8DispMain-Power-Average OBJECT-TYPE
	SYNTAX      Integer32
	MAX-ACCESS  read-only
	STATUS      current
	DESCRIPTION
		" PoutAvr, unit: 0.1 dB"
        ::= { amp8Disp-Main 5 }

amp8DispMain-Power-In OBJECT-TYPE
	SYNTAX      Integer32
	MAX-ACCESS  read-only
	STATUS      current
	DESCRIPTION
		"Pin, unit: 0.1 dB (-100000 = Unused)"
        ::= { amp8Disp-Main 6 }

amp8DispMain-Power-Ref OBJECT-TYPE
	SYNTAX      Integer32
	MAX-ACCESS  read-only
	STATUS      current
	DESCRIPTION
		"Pref, unit: 1/0.1/0.01 W / 1/0.1/0.01 dB, divider from ampXAux-PowerRef-Divider"
        ::= { amp8Disp-Main 7 }

amp8DispMain-Kp     OBJECT-TYPE
	SYNTAX      Integer32
	MAX-ACCESS  read-only
	STATUS      current
	DESCRIPTION
		"Kp, unit: 0.01 % (-100000 = Unused)"
        ::= { amp8Disp-Main 8 }

amp8DispMain-Phase  OBJECT-TYPE
	SYNTAX      Integer32
	MAX-ACCESS  read-only
	STATUS      current
	DESCRIPTION
		"Phase, unit: 0.1 % (-100000 = Unused)"
        ::= { amp8Disp-Main 9 }

amp8DispMain-dKp    OBJECT-TYPE
	SYNTAX      Integer32
	MAX-ACCESS  read-only
	STATUS      current
	DESCRIPTION
		"dKp, unit: 0.01 % (-100000 = Disabled)"
        ::= { amp8Disp-Main 10 }

amp8DispMain-Power-Out-2 OBJECT-TYPE
	SYNTAX      Integer32
	MAX-ACCESS  read-only
	STATUS      current
	DESCRIPTION
		"Pout2, unit: 1 W (-1 = Unused)"
        ::= { amp8Disp-Main 11 }

amp8DispMain-Profile OBJECT-TYPE
	SYNTAX      INTEGER {m1 (0), m2 (1)}
	MAX-ACCESS  read-only
	STATUS      current
	DESCRIPTION
		""
        ::= { amp8Disp-Main 12 }

amp8Aux-Status      OBJECT-TYPE
	SYNTAX      INTEGER {noFailure (0), powerOut (1), powerRef (2), powerIn (3), temperature1 (4), temperature2 (5), i1 (6), i2 (7), i3 (8), i4 (9), i5 (10), i6 (11), i7 (12), i8 (13), i9 (14), i10 (15), i11 (16), i12 (17), i13 (18), i14 (19), i15 (20), i16 (21), i17 (22), i18 (23), i19 (24), powerOutAvg (25), interErr (26), misc (31)}
	MAX-ACCESS  read-only
	STATUS      current
	DESCRIPTION
		"Amplifier internal failure status"
        ::= { amp8-Auxiliary 1 }

amp8Aux-Power-Units OBJECT-TYPE
	SYNTAX      INTEGER {none (0), watt (1), dB (2)}
	MAX-ACCESS  read-only
	STATUS      current
	DESCRIPTION
		"Amplifier Pout/Pref units: 1-W, 2-dB"
        ::= { amp8-Auxiliary 2 }

amp8Aux-Temperatures-Count OBJECT-TYPE
	SYNTAX      Integer32
	MAX-ACCESS  read-only
	STATUS      current
	DESCRIPTION
		"Temperatures sensors total count"
        ::= { amp8-Auxiliary 3 }

amp8Aux-Currents-Count OBJECT-TYPE
	SYNTAX      Integer32
	MAX-ACCESS  read-only
	STATUS      current
	DESCRIPTION
		"Currents sensors total count"
        ::= { amp8-Auxiliary 4 }

amp8Aux-Show-PowerOut-Only OBJECT-TYPE
	SYNTAX      INTEGER {false(0), true(1)}
	MAX-ACCESS  read-only
	STATUS      current
	DESCRIPTION
		"Display Pout only for main props: 0-No, 1-Yes"
        ::= { amp8-Auxiliary 5 }

amp8Aux-Show-PowerOut-Average OBJECT-TYPE
	SYNTAX      INTEGER {false(0), true(1)}
	MAX-ACCESS  read-only
	STATUS      current
	DESCRIPTION
		"Display Poutavg: 0-No, 1-Yes"
        ::= { amp8-Auxiliary 6 }

amp8Aux-Currents-Units OBJECT-TYPE
	SYNTAX      INTEGER {none (0), amper (1), percent (2)}
	MAX-ACCESS  read-only
	STATUS      current
	DESCRIPTION
		"Amplifier currents units: 1-Amperes (A), 2-Percent (%)"
        ::= { amp8-Auxiliary 7 }

amp8Aux-Show-dKp    OBJECT-TYPE
	SYNTAX      INTEGER {false(0), true(1)}
	MAX-ACCESS  read-only
	STATUS      current
	DESCRIPTION
		"Display dKp: 0-No, 1-Yes"
        ::= { amp8-Auxiliary 8 }

amp8Aux-PowerRef-Divider OBJECT-TYPE
	SYNTAX      Integer32
	MAX-ACCESS  read-only
	STATUS      current
	DESCRIPTION
		"Amplifier Pref divider: 1, 10, 100"
        ::= { amp8-Auxiliary 9 }

amp8Aux-Features    OBJECT-TYPE
	SYNTAX      Integer32
	MAX-ACCESS  read-only
	STATUS      current
	DESCRIPTION
		"Amplifier features/supports"
        ::= { amp8-Auxiliary 10 }

amp8Aux-Temperatures-Mapping OBJECT-TYPE
	SYNTAX      INTEGER {t1_T2 (0), tmax_Tps (1)}
	MAX-ACCESS  read-only
	STATUS      current
	DESCRIPTION
		"Temperatures titles mapping"
        ::= { amp8-Auxiliary 11 }

amp8Unit-Connected  OBJECT-TYPE
	SYNTAX      INTEGER {false(0), true(1)}
	MAX-ACCESS  read-only
	STATUS      current
	DESCRIPTION
		""
        ::= { amp8-Unit 1 }

amp8Unit-Warning    OBJECT-TYPE
	SYNTAX      INTEGER {false(0), true(1)}
	MAX-ACCESS  read-only
	STATUS      current
	DESCRIPTION
		""
        ::= { amp8-Unit 2 }

amp8Unit-Failure    OBJECT-TYPE
	SYNTAX      INTEGER {false(0), true(1)}
	MAX-ACCESS  read-only
	STATUS      current
	DESCRIPTION
		""
        ::= { amp8-Unit 3 }

amp8Unit-Busy       OBJECT-TYPE
	SYNTAX      Integer32
	MAX-ACCESS  read-only
	STATUS      current
	DESCRIPTION
		""
        ::= { amp8-Unit 4 }

amp8Unit-Model      OBJECT-TYPE
	SYNTAX      OCTET STRING
	MAX-ACCESS  read-only
	STATUS      current
	DESCRIPTION
		""
        ::= { amp8-Unit 5 }

amp8Unit-Serial-Number OBJECT-TYPE
	SYNTAX      Integer32
	MAX-ACCESS  read-only
	STATUS      current
	DESCRIPTION
		""
        ::= { amp8-Unit 6 }

amp8Unit-Firmware-Version OBJECT-TYPE
	SYNTAX      OCTET STRING
	MAX-ACCESS  read-only
	STATUS      current
	DESCRIPTION
		""
        ::= { amp8-Unit 7 }

amp8Unit-Uptime     OBJECT-TYPE
	SYNTAX      DateAndTime
	MAX-ACCESS  read-only
	STATUS      current
	DESCRIPTION
		""
        ::= { amp8-Unit 8 }

amp8Unit-Post-Writes-Count OBJECT-TYPE
	SYNTAX      Integer32
	MAX-ACCESS  read-only
	STATUS      current
	DESCRIPTION
		""
        ::= { amp8-Unit 9 }

amp8Unit-IP-Address OBJECT-TYPE
	SYNTAX      IPAddress
	MAX-ACCESS  read-only
	STATUS      current
	DESCRIPTION
		""
        ::= { amp8-Unit 10 }

amp8Unit-TCP-Port   OBJECT-TYPE
	SYNTAX      Integer32
	MAX-ACCESS  read-only
	STATUS      current
	DESCRIPTION
		""
        ::= { amp8-Unit 11 }

amp8Unit-Adapter    OBJECT-TYPE
	SYNTAX      OCTET STRING
	MAX-ACCESS  read-only
	STATUS      current
	DESCRIPTION
		""
        ::= { amp8-Unit 12 }

amp8Unit-Reconnects OBJECT-TYPE
	SYNTAX      Integer32
	MAX-ACCESS  read-only
	STATUS      current
	DESCRIPTION
		""
        ::= { amp8-Unit 13 }

amp7DispCurs-Div-Current-Divider-1 OBJECT-TYPE
	SYNTAX      Integer32
	MAX-ACCESS  read-only
	STATUS      current
	DESCRIPTION
		""
        ::= { amp7Disp-Currents-Dividers 1 }

amp7DispCurs-Div-Current-Divider-2 OBJECT-TYPE
	SYNTAX      Integer32
	MAX-ACCESS  read-only
	STATUS      current
	DESCRIPTION
		""
        ::= { amp7Disp-Currents-Dividers 2 }

amp7DispCurs-Div-Current-Divider-3 OBJECT-TYPE
	SYNTAX      Integer32
	MAX-ACCESS  read-only
	STATUS      current
	DESCRIPTION
		""
        ::= { amp7Disp-Currents-Dividers 3 }

amp7DispCurs-Div-Current-Divider-4 OBJECT-TYPE
	SYNTAX      Integer32
	MAX-ACCESS  read-only
	STATUS      current
	DESCRIPTION
		""
        ::= { amp7Disp-Currents-Dividers 4 }

amp7DispCurs-Div-Current-Divider-5 OBJECT-TYPE
	SYNTAX      Integer32
	MAX-ACCESS  read-only
	STATUS      current
	DESCRIPTION
		""
        ::= { amp7Disp-Currents-Dividers 5 }

amp7DispCurs-Div-Current-Divider-6 OBJECT-TYPE
	SYNTAX      Integer32
	MAX-ACCESS  read-only
	STATUS      current
	DESCRIPTION
		""
        ::= { amp7Disp-Currents-Dividers 6 }

amp7DispCurs-Div-Current-Divider-7 OBJECT-TYPE
	SYNTAX      Integer32
	MAX-ACCESS  read-only
	STATUS      current
	DESCRIPTION
		""
        ::= { amp7Disp-Currents-Dividers 7 }

amp7DispCurs-Div-Current-Divider-8 OBJECT-TYPE
	SYNTAX      Integer32
	MAX-ACCESS  read-only
	STATUS      current
	DESCRIPTION
		""
        ::= { amp7Disp-Currents-Dividers 8 }

amp7DispCurs-Div-Current-Divider-9 OBJECT-TYPE
	SYNTAX      Integer32
	MAX-ACCESS  read-only
	STATUS      current
	DESCRIPTION
		""
        ::= { amp7Disp-Currents-Dividers 9 }

amp7DispCurs-Div-Current-Divider-10 OBJECT-TYPE
	SYNTAX      Integer32
	MAX-ACCESS  read-only
	STATUS      current
	DESCRIPTION
		""
        ::= { amp7Disp-Currents-Dividers 10 }

amp7DispCurs-Div-Current-Divider-11 OBJECT-TYPE
	SYNTAX      Integer32
	MAX-ACCESS  read-only
	STATUS      current
	DESCRIPTION
		""
        ::= { amp7Disp-Currents-Dividers 11 }

amp7DispCurs-Div-Current-Divider-12 OBJECT-TYPE
	SYNTAX      Integer32
	MAX-ACCESS  read-only
	STATUS      current
	DESCRIPTION
		""
        ::= { amp7Disp-Currents-Dividers 12 }

amp7DispCurs-Div-Current-Divider-13 OBJECT-TYPE
	SYNTAX      Integer32
	MAX-ACCESS  read-only
	STATUS      current
	DESCRIPTION
		""
        ::= { amp7Disp-Currents-Dividers 13 }

amp7DispCurs-Div-Current-Divider-14 OBJECT-TYPE
	SYNTAX      Integer32
	MAX-ACCESS  read-only
	STATUS      current
	DESCRIPTION
		""
        ::= { amp7Disp-Currents-Dividers 14 }

amp7DispCurs-Div-Current-Divider-15 OBJECT-TYPE
	SYNTAX      Integer32
	MAX-ACCESS  read-only
	STATUS      current
	DESCRIPTION
		""
        ::= { amp7Disp-Currents-Dividers 15 }

amp7DispCurs-Div-Current-Divider-16 OBJECT-TYPE
	SYNTAX      Integer32
	MAX-ACCESS  read-only
	STATUS      current
	DESCRIPTION
		""
        ::= { amp7Disp-Currents-Dividers 16 }

amp7DispCurs-Div-Current-Divider-17 OBJECT-TYPE
	SYNTAX      Integer32
	MAX-ACCESS  read-only
	STATUS      current
	DESCRIPTION
		""
        ::= { amp7Disp-Currents-Dividers 17 }

amp7DispCurs-Div-Current-Divider-18 OBJECT-TYPE
	SYNTAX      Integer32
	MAX-ACCESS  read-only
	STATUS      current
	DESCRIPTION
		""
        ::= { amp7Disp-Currents-Dividers 18 }

amp7DispCurs-Div-Current-Divider-19 OBJECT-TYPE
	SYNTAX      Integer32
	MAX-ACCESS  read-only
	STATUS      current
	DESCRIPTION
		""
        ::= { amp7Disp-Currents-Dividers 19 }

amp7DispCurs-Current-1 OBJECT-TYPE
	SYNTAX      Integer32
	MAX-ACCESS  read-only
	STATUS      current
	DESCRIPTION
		""
        ::= { amp7Disp-Currents 1 }

amp7DispCurs-Current-2 OBJECT-TYPE
	SYNTAX      Integer32
	MAX-ACCESS  read-only
	STATUS      current
	DESCRIPTION
		""
        ::= { amp7Disp-Currents 2 }

amp7DispCurs-Current-3 OBJECT-TYPE
	SYNTAX      Integer32
	MAX-ACCESS  read-only
	STATUS      current
	DESCRIPTION
		""
        ::= { amp7Disp-Currents 3 }

amp7DispCurs-Current-4 OBJECT-TYPE
	SYNTAX      Integer32
	MAX-ACCESS  read-only
	STATUS      current
	DESCRIPTION
		""
        ::= { amp7Disp-Currents 4 }

amp7DispCurs-Current-5 OBJECT-TYPE
	SYNTAX      Integer32
	MAX-ACCESS  read-only
	STATUS      current
	DESCRIPTION
		""
        ::= { amp7Disp-Currents 5 }

amp7DispCurs-Current-6 OBJECT-TYPE
	SYNTAX      Integer32
	MAX-ACCESS  read-only
	STATUS      current
	DESCRIPTION
		""
        ::= { amp7Disp-Currents 6 }

amp7DispCurs-Current-7 OBJECT-TYPE
	SYNTAX      Integer32
	MAX-ACCESS  read-only
	STATUS      current
	DESCRIPTION
		""
        ::= { amp7Disp-Currents 7 }

amp7DispCurs-Current-8 OBJECT-TYPE
	SYNTAX      Integer32
	MAX-ACCESS  read-only
	STATUS      current
	DESCRIPTION
		""
        ::= { amp7Disp-Currents 8 }

amp7DispCurs-Current-9 OBJECT-TYPE
	SYNTAX      Integer32
	MAX-ACCESS  read-only
	STATUS      current
	DESCRIPTION
		""
        ::= { amp7Disp-Currents 9 }

amp7DispCurs-Current-10 OBJECT-TYPE
	SYNTAX      Integer32
	MAX-ACCESS  read-only
	STATUS      current
	DESCRIPTION
		""
        ::= { amp7Disp-Currents 10 }

amp7DispCurs-Current-11 OBJECT-TYPE
	SYNTAX      Integer32
	MAX-ACCESS  read-only
	STATUS      current
	DESCRIPTION
		""
        ::= { amp7Disp-Currents 11 }

amp7DispCurs-Current-12 OBJECT-TYPE
	SYNTAX      Integer32
	MAX-ACCESS  read-only
	STATUS      current
	DESCRIPTION
		""
        ::= { amp7Disp-Currents 12 }

amp7DispCurs-Current-13 OBJECT-TYPE
	SYNTAX      Integer32
	MAX-ACCESS  read-only
	STATUS      current
	DESCRIPTION
		""
        ::= { amp7Disp-Currents 13 }

amp7DispCurs-Current-14 OBJECT-TYPE
	SYNTAX      Integer32
	MAX-ACCESS  read-only
	STATUS      current
	DESCRIPTION
		""
        ::= { amp7Disp-Currents 14 }

amp7DispCurs-Current-15 OBJECT-TYPE
	SYNTAX      Integer32
	MAX-ACCESS  read-only
	STATUS      current
	DESCRIPTION
		""
        ::= { amp7Disp-Currents 15 }

amp7DispCurs-Current-16 OBJECT-TYPE
	SYNTAX      Integer32
	MAX-ACCESS  read-only
	STATUS      current
	DESCRIPTION
		""
        ::= { amp7Disp-Currents 16 }

amp7DispCurs-Current-17 OBJECT-TYPE
	SYNTAX      Integer32
	MAX-ACCESS  read-only
	STATUS      current
	DESCRIPTION
		""
        ::= { amp7Disp-Currents 17 }

amp7DispCurs-Current-18 OBJECT-TYPE
	SYNTAX      Integer32
	MAX-ACCESS  read-only
	STATUS      current
	DESCRIPTION
		""
        ::= { amp7Disp-Currents 18 }

amp7DispCurs-Current-19 OBJECT-TYPE
	SYNTAX      Integer32
	MAX-ACCESS  read-only
	STATUS      current
	DESCRIPTION
		""
        ::= { amp7Disp-Currents 19 }

amp7DispTemps-Temperature-1 OBJECT-TYPE
	SYNTAX      Integer32
	MAX-ACCESS  read-only
	STATUS      current
	DESCRIPTION
		""
        ::= { amp7Disp-Temperatures 1 }

amp7DispTemps-Temperature-2 OBJECT-TYPE
	SYNTAX      Integer32
	MAX-ACCESS  read-only
	STATUS      current
	DESCRIPTION
		""
        ::= { amp7Disp-Temperatures 2 }

amp7DispMain-Status-Info OBJECT-TYPE
	SYNTAX      OCTET STRING
	MAX-ACCESS  read-only
	STATUS      current
	DESCRIPTION
		"Multiline, UTF8, separator: CRLF"
        ::= { amp7Disp-Main 1 }

amp7DispMain-Status-Warning OBJECT-TYPE
	SYNTAX      OCTET STRING
	MAX-ACCESS  read-only
	STATUS      current
	DESCRIPTION
		"Multiline, UTF8, separator: CRLF"
        ::= { amp7Disp-Main 2 }

amp7DispMain-Status-Failure OBJECT-TYPE
	SYNTAX      OCTET STRING
	MAX-ACCESS  read-only
	STATUS      current
	DESCRIPTION
		"Multiline, UTF8, separator: CRLF"
        ::= { amp7Disp-Main 3 }

amp7DispMain-Power-Out OBJECT-TYPE
	SYNTAX      Integer32
	MAX-ACCESS  read-only
	STATUS      current
	DESCRIPTION
		"Pout, unit: 0.1 W / 0.1 dB"
        ::= { amp7Disp-Main 4 }

amp7DispMain-Power-Average OBJECT-TYPE
	SYNTAX      Integer32
	MAX-ACCESS  read-only
	STATUS      current
	DESCRIPTION
		" PoutAvr, unit: 0.1 dB"
        ::= { amp7Disp-Main 5 }

amp7DispMain-Power-In OBJECT-TYPE
	SYNTAX      Integer32
	MAX-ACCESS  read-only
	STATUS      current
	DESCRIPTION
		"Pin, unit: 0.1 dB (-100000 = Unused)"
        ::= { amp7Disp-Main 6 }

amp7DispMain-Power-Ref OBJECT-TYPE
	SYNTAX      Integer32
	MAX-ACCESS  read-only
	STATUS      current
	DESCRIPTION
		"Pref, unit: 1/0.1/0.01 W / 1/0.1/0.01 dB, divider from ampXAux-PowerRef-Divider"
        ::= { amp7Disp-Main 7 }

amp7DispMain-Kp     OBJECT-TYPE
	SYNTAX      Integer32
	MAX-ACCESS  read-only
	STATUS      current
	DESCRIPTION
		"Kp, unit: 0.01 % (-100000 = Unused)"
        ::= { amp7Disp-Main 8 }

amp7DispMain-Phase  OBJECT-TYPE
	SYNTAX      Integer32
	MAX-ACCESS  read-only
	STATUS      current
	DESCRIPTION
		"Phase, unit: 0.1 % (-100000 = Unused)"
        ::= { amp7Disp-Main 9 }

amp7DispMain-dKp    OBJECT-TYPE
	SYNTAX      Integer32
	MAX-ACCESS  read-only
	STATUS      current
	DESCRIPTION
		"dKp, unit: 0.01 % (-100000 = Disabled)"
        ::= { amp7Disp-Main 10 }

amp7DispMain-Power-Out-2 OBJECT-TYPE
	SYNTAX      Integer32
	MAX-ACCESS  read-only
	STATUS      current
	DESCRIPTION
		"Pout2, unit: 1 W (-1 = Unused)"
        ::= { amp7Disp-Main 11 }

amp7DispMain-Profile OBJECT-TYPE
	SYNTAX      INTEGER {m1 (0), m2 (1)}
	MAX-ACCESS  read-only
	STATUS      current
	DESCRIPTION
		""
        ::= { amp7Disp-Main 12 }

amp7Aux-Status      OBJECT-TYPE
	SYNTAX      INTEGER {noFailure (0), powerOut (1), powerRef (2), powerIn (3), temperature1 (4), temperature2 (5), i1 (6), i2 (7), i3 (8), i4 (9), i5 (10), i6 (11), i7 (12), i8 (13), i9 (14), i10 (15), i11 (16), i12 (17), i13 (18), i14 (19), i15 (20), i16 (21), i17 (22), i18 (23), i19 (24), powerOutAvg (25), interErr (26), misc (31)}
	MAX-ACCESS  read-only
	STATUS      current
	DESCRIPTION
		"Amplifier internal failure status"
        ::= { amp7-Auxiliary 1 }

amp7Aux-Power-Units OBJECT-TYPE
	SYNTAX      INTEGER {none (0), watt (1), dB (2)}
	MAX-ACCESS  read-only
	STATUS      current
	DESCRIPTION
		"Amplifier Pout/Pref units: 1-W, 2-dB"
        ::= { amp7-Auxiliary 2 }

amp7Aux-Temperatures-Count OBJECT-TYPE
	SYNTAX      Integer32
	MAX-ACCESS  read-only
	STATUS      current
	DESCRIPTION
		"Temperatures sensors total count"
        ::= { amp7-Auxiliary 3 }

amp7Aux-Currents-Count OBJECT-TYPE
	SYNTAX      Integer32
	MAX-ACCESS  read-only
	STATUS      current
	DESCRIPTION
		"Currents sensors total count"
        ::= { amp7-Auxiliary 4 }

amp7Aux-Show-PowerOut-Only OBJECT-TYPE
	SYNTAX      INTEGER {false(0), true(1)}
	MAX-ACCESS  read-only
	STATUS      current
	DESCRIPTION
		"Display Pout only for main props: 0-No, 1-Yes"
        ::= { amp7-Auxiliary 5 }

amp7Aux-Show-PowerOut-Average OBJECT-TYPE
	SYNTAX      INTEGER {false(0), true(1)}
	MAX-ACCESS  read-only
	STATUS      current
	DESCRIPTION
		"Display Poutavg: 0-No, 1-Yes"
        ::= { amp7-Auxiliary 6 }

amp7Aux-Currents-Units OBJECT-TYPE
	SYNTAX      INTEGER {none (0), amper (1), percent (2)}
	MAX-ACCESS  read-only
	STATUS      current
	DESCRIPTION
		"Amplifier currents units: 1-Amperes (A), 2-Percent (%)"
        ::= { amp7-Auxiliary 7 }

amp7Aux-Show-dKp    OBJECT-TYPE
	SYNTAX      INTEGER {false(0), true(1)}
	MAX-ACCESS  read-only
	STATUS      current
	DESCRIPTION
		"Display dKp: 0-No, 1-Yes"
        ::= { amp7-Auxiliary 8 }

amp7Aux-PowerRef-Divider OBJECT-TYPE
	SYNTAX      Integer32
	MAX-ACCESS  read-only
	STATUS      current
	DESCRIPTION
		"Amplifier Pref divider: 1, 10, 100"
        ::= { amp7-Auxiliary 9 }

amp7Aux-Features    OBJECT-TYPE
	SYNTAX      Integer32
	MAX-ACCESS  read-only
	STATUS      current
	DESCRIPTION
		"Amplifier features/supports"
        ::= { amp7-Auxiliary 10 }

amp7Aux-Temperatures-Mapping OBJECT-TYPE
	SYNTAX      INTEGER {t1_T2 (0), tmax_Tps (1)}
	MAX-ACCESS  read-only
	STATUS      current
	DESCRIPTION
		"Temperatures titles mapping"
        ::= { amp7-Auxiliary 11 }

amp7Unit-Connected  OBJECT-TYPE
	SYNTAX      INTEGER {false(0), true(1)}
	MAX-ACCESS  read-only
	STATUS      current
	DESCRIPTION
		""
        ::= { amp7-Unit 1 }

amp7Unit-Warning    OBJECT-TYPE
	SYNTAX      INTEGER {false(0), true(1)}
	MAX-ACCESS  read-only
	STATUS      current
	DESCRIPTION
		""
        ::= { amp7-Unit 2 }

amp7Unit-Failure    OBJECT-TYPE
	SYNTAX      INTEGER {false(0), true(1)}
	MAX-ACCESS  read-only
	STATUS      current
	DESCRIPTION
		""
        ::= { amp7-Unit 3 }

amp7Unit-Busy       OBJECT-TYPE
	SYNTAX      Integer32
	MAX-ACCESS  read-only
	STATUS      current
	DESCRIPTION
		""
        ::= { amp7-Unit 4 }

amp7Unit-Model      OBJECT-TYPE
	SYNTAX      OCTET STRING
	MAX-ACCESS  read-only
	STATUS      current
	DESCRIPTION
		""
        ::= { amp7-Unit 5 }

amp7Unit-Serial-Number OBJECT-TYPE
	SYNTAX      Integer32
	MAX-ACCESS  read-only
	STATUS      current
	DESCRIPTION
		""
        ::= { amp7-Unit 6 }

amp7Unit-Firmware-Version OBJECT-TYPE
	SYNTAX      OCTET STRING
	MAX-ACCESS  read-only
	STATUS      current
	DESCRIPTION
		""
        ::= { amp7-Unit 7 }

amp7Unit-Uptime     OBJECT-TYPE
	SYNTAX      DateAndTime
	MAX-ACCESS  read-only
	STATUS      current
	DESCRIPTION
		""
        ::= { amp7-Unit 8 }

amp7Unit-Post-Writes-Count OBJECT-TYPE
	SYNTAX      Integer32
	MAX-ACCESS  read-only
	STATUS      current
	DESCRIPTION
		""
        ::= { amp7-Unit 9 }

amp7Unit-IP-Address OBJECT-TYPE
	SYNTAX      IPAddress
	MAX-ACCESS  read-only
	STATUS      current
	DESCRIPTION
		""
        ::= { amp7-Unit 10 }

amp7Unit-TCP-Port   OBJECT-TYPE
	SYNTAX      Integer32
	MAX-ACCESS  read-only
	STATUS      current
	DESCRIPTION
		""
        ::= { amp7-Unit 11 }

amp7Unit-Adapter    OBJECT-TYPE
	SYNTAX      OCTET STRING
	MAX-ACCESS  read-only
	STATUS      current
	DESCRIPTION
		""
        ::= { amp7-Unit 12 }

amp7Unit-Reconnects OBJECT-TYPE
	SYNTAX      Integer32
	MAX-ACCESS  read-only
	STATUS      current
	DESCRIPTION
		""
        ::= { amp7-Unit 13 }

amp6DispCurs-Div-Current-Divider-1 OBJECT-TYPE
	SYNTAX      Integer32
	MAX-ACCESS  read-only
	STATUS      current
	DESCRIPTION
		""
        ::= { amp6Disp-Currents-Dividers 1 }

amp6DispCurs-Div-Current-Divider-2 OBJECT-TYPE
	SYNTAX      Integer32
	MAX-ACCESS  read-only
	STATUS      current
	DESCRIPTION
		""
        ::= { amp6Disp-Currents-Dividers 2 }

amp6DispCurs-Div-Current-Divider-3 OBJECT-TYPE
	SYNTAX      Integer32
	MAX-ACCESS  read-only
	STATUS      current
	DESCRIPTION
		""
        ::= { amp6Disp-Currents-Dividers 3 }

amp6DispCurs-Div-Current-Divider-4 OBJECT-TYPE
	SYNTAX      Integer32
	MAX-ACCESS  read-only
	STATUS      current
	DESCRIPTION
		""
        ::= { amp6Disp-Currents-Dividers 4 }

amp6DispCurs-Div-Current-Divider-5 OBJECT-TYPE
	SYNTAX      Integer32
	MAX-ACCESS  read-only
	STATUS      current
	DESCRIPTION
		""
        ::= { amp6Disp-Currents-Dividers 5 }

amp6DispCurs-Div-Current-Divider-6 OBJECT-TYPE
	SYNTAX      Integer32
	MAX-ACCESS  read-only
	STATUS      current
	DESCRIPTION
		""
        ::= { amp6Disp-Currents-Dividers 6 }

amp6DispCurs-Div-Current-Divider-7 OBJECT-TYPE
	SYNTAX      Integer32
	MAX-ACCESS  read-only
	STATUS      current
	DESCRIPTION
		""
        ::= { amp6Disp-Currents-Dividers 7 }

amp6DispCurs-Div-Current-Divider-8 OBJECT-TYPE
	SYNTAX      Integer32
	MAX-ACCESS  read-only
	STATUS      current
	DESCRIPTION
		""
        ::= { amp6Disp-Currents-Dividers 8 }

amp6DispCurs-Div-Current-Divider-9 OBJECT-TYPE
	SYNTAX      Integer32
	MAX-ACCESS  read-only
	STATUS      current
	DESCRIPTION
		""
        ::= { amp6Disp-Currents-Dividers 9 }

amp6DispCurs-Div-Current-Divider-10 OBJECT-TYPE
	SYNTAX      Integer32
	MAX-ACCESS  read-only
	STATUS      current
	DESCRIPTION
		""
        ::= { amp6Disp-Currents-Dividers 10 }

amp6DispCurs-Div-Current-Divider-11 OBJECT-TYPE
	SYNTAX      Integer32
	MAX-ACCESS  read-only
	STATUS      current
	DESCRIPTION
		""
        ::= { amp6Disp-Currents-Dividers 11 }

amp6DispCurs-Div-Current-Divider-12 OBJECT-TYPE
	SYNTAX      Integer32
	MAX-ACCESS  read-only
	STATUS      current
	DESCRIPTION
		""
        ::= { amp6Disp-Currents-Dividers 12 }

amp6DispCurs-Div-Current-Divider-13 OBJECT-TYPE
	SYNTAX      Integer32
	MAX-ACCESS  read-only
	STATUS      current
	DESCRIPTION
		""
        ::= { amp6Disp-Currents-Dividers 13 }

amp6DispCurs-Div-Current-Divider-14 OBJECT-TYPE
	SYNTAX      Integer32
	MAX-ACCESS  read-only
	STATUS      current
	DESCRIPTION
		""
        ::= { amp6Disp-Currents-Dividers 14 }

amp6DispCurs-Div-Current-Divider-15 OBJECT-TYPE
	SYNTAX      Integer32
	MAX-ACCESS  read-only
	STATUS      current
	DESCRIPTION
		""
        ::= { amp6Disp-Currents-Dividers 15 }

amp6DispCurs-Div-Current-Divider-16 OBJECT-TYPE
	SYNTAX      Integer32
	MAX-ACCESS  read-only
	STATUS      current
	DESCRIPTION
		""
        ::= { amp6Disp-Currents-Dividers 16 }

amp6DispCurs-Div-Current-Divider-17 OBJECT-TYPE
	SYNTAX      Integer32
	MAX-ACCESS  read-only
	STATUS      current
	DESCRIPTION
		""
        ::= { amp6Disp-Currents-Dividers 17 }

amp6DispCurs-Div-Current-Divider-18 OBJECT-TYPE
	SYNTAX      Integer32
	MAX-ACCESS  read-only
	STATUS      current
	DESCRIPTION
		""
        ::= { amp6Disp-Currents-Dividers 18 }

amp6DispCurs-Div-Current-Divider-19 OBJECT-TYPE
	SYNTAX      Integer32
	MAX-ACCESS  read-only
	STATUS      current
	DESCRIPTION
		""
        ::= { amp6Disp-Currents-Dividers 19 }

amp6DispCurs-Current-1 OBJECT-TYPE
	SYNTAX      Integer32
	MAX-ACCESS  read-only
	STATUS      current
	DESCRIPTION
		""
        ::= { amp6Disp-Currents 1 }

amp6DispCurs-Current-2 OBJECT-TYPE
	SYNTAX      Integer32
	MAX-ACCESS  read-only
	STATUS      current
	DESCRIPTION
		""
        ::= { amp6Disp-Currents 2 }

amp6DispCurs-Current-3 OBJECT-TYPE
	SYNTAX      Integer32
	MAX-ACCESS  read-only
	STATUS      current
	DESCRIPTION
		""
        ::= { amp6Disp-Currents 3 }

amp6DispCurs-Current-4 OBJECT-TYPE
	SYNTAX      Integer32
	MAX-ACCESS  read-only
	STATUS      current
	DESCRIPTION
		""
        ::= { amp6Disp-Currents 4 }

amp6DispCurs-Current-5 OBJECT-TYPE
	SYNTAX      Integer32
	MAX-ACCESS  read-only
	STATUS      current
	DESCRIPTION
		""
        ::= { amp6Disp-Currents 5 }

amp6DispCurs-Current-6 OBJECT-TYPE
	SYNTAX      Integer32
	MAX-ACCESS  read-only
	STATUS      current
	DESCRIPTION
		""
        ::= { amp6Disp-Currents 6 }

amp6DispCurs-Current-7 OBJECT-TYPE
	SYNTAX      Integer32
	MAX-ACCESS  read-only
	STATUS      current
	DESCRIPTION
		""
        ::= { amp6Disp-Currents 7 }

amp6DispCurs-Current-8 OBJECT-TYPE
	SYNTAX      Integer32
	MAX-ACCESS  read-only
	STATUS      current
	DESCRIPTION
		""
        ::= { amp6Disp-Currents 8 }

amp6DispCurs-Current-9 OBJECT-TYPE
	SYNTAX      Integer32
	MAX-ACCESS  read-only
	STATUS      current
	DESCRIPTION
		""
        ::= { amp6Disp-Currents 9 }

amp6DispCurs-Current-10 OBJECT-TYPE
	SYNTAX      Integer32
	MAX-ACCESS  read-only
	STATUS      current
	DESCRIPTION
		""
        ::= { amp6Disp-Currents 10 }

amp6DispCurs-Current-11 OBJECT-TYPE
	SYNTAX      Integer32
	MAX-ACCESS  read-only
	STATUS      current
	DESCRIPTION
		""
        ::= { amp6Disp-Currents 11 }

amp6DispCurs-Current-12 OBJECT-TYPE
	SYNTAX      Integer32
	MAX-ACCESS  read-only
	STATUS      current
	DESCRIPTION
		""
        ::= { amp6Disp-Currents 12 }

amp6DispCurs-Current-13 OBJECT-TYPE
	SYNTAX      Integer32
	MAX-ACCESS  read-only
	STATUS      current
	DESCRIPTION
		""
        ::= { amp6Disp-Currents 13 }

amp6DispCurs-Current-14 OBJECT-TYPE
	SYNTAX      Integer32
	MAX-ACCESS  read-only
	STATUS      current
	DESCRIPTION
		""
        ::= { amp6Disp-Currents 14 }

amp6DispCurs-Current-15 OBJECT-TYPE
	SYNTAX      Integer32
	MAX-ACCESS  read-only
	STATUS      current
	DESCRIPTION
		""
        ::= { amp6Disp-Currents 15 }

amp6DispCurs-Current-16 OBJECT-TYPE
	SYNTAX      Integer32
	MAX-ACCESS  read-only
	STATUS      current
	DESCRIPTION
		""
        ::= { amp6Disp-Currents 16 }

amp6DispCurs-Current-17 OBJECT-TYPE
	SYNTAX      Integer32
	MAX-ACCESS  read-only
	STATUS      current
	DESCRIPTION
		""
        ::= { amp6Disp-Currents 17 }

amp6DispCurs-Current-18 OBJECT-TYPE
	SYNTAX      Integer32
	MAX-ACCESS  read-only
	STATUS      current
	DESCRIPTION
		""
        ::= { amp6Disp-Currents 18 }

amp6DispCurs-Current-19 OBJECT-TYPE
	SYNTAX      Integer32
	MAX-ACCESS  read-only
	STATUS      current
	DESCRIPTION
		""
        ::= { amp6Disp-Currents 19 }

amp6DispTemps-Temperature-1 OBJECT-TYPE
	SYNTAX      Integer32
	MAX-ACCESS  read-only
	STATUS      current
	DESCRIPTION
		""
        ::= { amp6Disp-Temperatures 1 }

amp6DispTemps-Temperature-2 OBJECT-TYPE
	SYNTAX      Integer32
	MAX-ACCESS  read-only
	STATUS      current
	DESCRIPTION
		""
        ::= { amp6Disp-Temperatures 2 }

amp6DispMain-Status-Info OBJECT-TYPE
	SYNTAX      OCTET STRING
	MAX-ACCESS  read-only
	STATUS      current
	DESCRIPTION
		"Multiline, UTF8, separator: CRLF"
        ::= { amp6Disp-Main 1 }

amp6DispMain-Status-Warning OBJECT-TYPE
	SYNTAX      OCTET STRING
	MAX-ACCESS  read-only
	STATUS      current
	DESCRIPTION
		"Multiline, UTF8, separator: CRLF"
        ::= { amp6Disp-Main 2 }

amp6DispMain-Status-Failure OBJECT-TYPE
	SYNTAX      OCTET STRING
	MAX-ACCESS  read-only
	STATUS      current
	DESCRIPTION
		"Multiline, UTF8, separator: CRLF"
        ::= { amp6Disp-Main 3 }

amp6DispMain-Power-Out OBJECT-TYPE
	SYNTAX      Integer32
	MAX-ACCESS  read-only
	STATUS      current
	DESCRIPTION
		"Pout, unit: 0.1 W / 0.1 dB"
        ::= { amp6Disp-Main 4 }

amp6DispMain-Power-Average OBJECT-TYPE
	SYNTAX      Integer32
	MAX-ACCESS  read-only
	STATUS      current
	DESCRIPTION
		" PoutAvr, unit: 0.1 dB"
        ::= { amp6Disp-Main 5 }

amp6DispMain-Power-In OBJECT-TYPE
	SYNTAX      Integer32
	MAX-ACCESS  read-only
	STATUS      current
	DESCRIPTION
		"Pin, unit: 0.1 dB (-100000 = Unused)"
        ::= { amp6Disp-Main 6 }

amp6DispMain-Power-Ref OBJECT-TYPE
	SYNTAX      Integer32
	MAX-ACCESS  read-only
	STATUS      current
	DESCRIPTION
		"Pref, unit: 1/0.1/0.01 W / 1/0.1/0.01 dB, divider from ampXAux-PowerRef-Divider"
        ::= { amp6Disp-Main 7 }

amp6DispMain-Kp     OBJECT-TYPE
	SYNTAX      Integer32
	MAX-ACCESS  read-only
	STATUS      current
	DESCRIPTION
		"Kp, unit: 0.01 % (-100000 = Unused)"
        ::= { amp6Disp-Main 8 }

amp6DispMain-Phase  OBJECT-TYPE
	SYNTAX      Integer32
	MAX-ACCESS  read-only
	STATUS      current
	DESCRIPTION
		"Phase, unit: 0.1 % (-100000 = Unused)"
        ::= { amp6Disp-Main 9 }

amp6DispMain-dKp    OBJECT-TYPE
	SYNTAX      Integer32
	MAX-ACCESS  read-only
	STATUS      current
	DESCRIPTION
		"dKp, unit: 0.01 % (-100000 = Disabled)"
        ::= { amp6Disp-Main 10 }

amp6DispMain-Power-Out-2 OBJECT-TYPE
	SYNTAX      Integer32
	MAX-ACCESS  read-only
	STATUS      current
	DESCRIPTION
		"Pout2, unit: 1 W (-1 = Unused)"
        ::= { amp6Disp-Main 11 }

amp6DispMain-Profile OBJECT-TYPE
	SYNTAX      INTEGER {m1 (0), m2 (1)}
	MAX-ACCESS  read-only
	STATUS      current
	DESCRIPTION
		""
        ::= { amp6Disp-Main 12 }

amp6Aux-Status      OBJECT-TYPE
	SYNTAX      INTEGER {noFailure (0), powerOut (1), powerRef (2), powerIn (3), temperature1 (4), temperature2 (5), i1 (6), i2 (7), i3 (8), i4 (9), i5 (10), i6 (11), i7 (12), i8 (13), i9 (14), i10 (15), i11 (16), i12 (17), i13 (18), i14 (19), i15 (20), i16 (21), i17 (22), i18 (23), i19 (24), powerOutAvg (25), interErr (26), misc (31)}
	MAX-ACCESS  read-only
	STATUS      current
	DESCRIPTION
		"Amplifier internal failure status"
        ::= { amp6-Auxiliary 1 }

amp6Aux-Power-Units OBJECT-TYPE
	SYNTAX      INTEGER {none (0), watt (1), dB (2)}
	MAX-ACCESS  read-only
	STATUS      current
	DESCRIPTION
		"Amplifier Pout/Pref units: 1-W, 2-dB"
        ::= { amp6-Auxiliary 2 }

amp6Aux-Temperatures-Count OBJECT-TYPE
	SYNTAX      Integer32
	MAX-ACCESS  read-only
	STATUS      current
	DESCRIPTION
		"Temperatures sensors total count"
        ::= { amp6-Auxiliary 3 }

amp6Aux-Currents-Count OBJECT-TYPE
	SYNTAX      Integer32
	MAX-ACCESS  read-only
	STATUS      current
	DESCRIPTION
		"Currents sensors total count"
        ::= { amp6-Auxiliary 4 }

amp6Aux-Show-PowerOut-Only OBJECT-TYPE
	SYNTAX      INTEGER {false(0), true(1)}
	MAX-ACCESS  read-only
	STATUS      current
	DESCRIPTION
		"Display Pout only for main props: 0-No, 1-Yes"
        ::= { amp6-Auxiliary 5 }

amp6Aux-Show-PowerOut-Average OBJECT-TYPE
	SYNTAX      INTEGER {false(0), true(1)}
	MAX-ACCESS  read-only
	STATUS      current
	DESCRIPTION
		"Display Poutavg: 0-No, 1-Yes"
        ::= { amp6-Auxiliary 6 }

amp6Aux-Currents-Units OBJECT-TYPE
	SYNTAX      INTEGER {none (0), amper (1), percent (2)}
	MAX-ACCESS  read-only
	STATUS      current
	DESCRIPTION
		"Amplifier currents units: 1-Amperes (A), 2-Percent (%)"
        ::= { amp6-Auxiliary 7 }

amp6Aux-Show-dKp    OBJECT-TYPE
	SYNTAX      INTEGER {false(0), true(1)}
	MAX-ACCESS  read-only
	STATUS      current
	DESCRIPTION
		"Display dKp: 0-No, 1-Yes"
        ::= { amp6-Auxiliary 8 }

amp6Aux-PowerRef-Divider OBJECT-TYPE
	SYNTAX      Integer32
	MAX-ACCESS  read-only
	STATUS      current
	DESCRIPTION
		"Amplifier Pref divider: 1, 10, 100"
        ::= { amp6-Auxiliary 9 }

amp6Aux-Features    OBJECT-TYPE
	SYNTAX      Integer32
	MAX-ACCESS  read-only
	STATUS      current
	DESCRIPTION
		"Amplifier features/supports"
        ::= { amp6-Auxiliary 10 }

amp6Aux-Temperatures-Mapping OBJECT-TYPE
	SYNTAX      INTEGER {t1_T2 (0), tmax_Tps (1)}
	MAX-ACCESS  read-only
	STATUS      current
	DESCRIPTION
		"Temperatures titles mapping"
        ::= { amp6-Auxiliary 11 }

amp6Unit-Connected  OBJECT-TYPE
	SYNTAX      INTEGER {false(0), true(1)}
	MAX-ACCESS  read-only
	STATUS      current
	DESCRIPTION
		""
        ::= { amp6-Unit 1 }

amp6Unit-Warning    OBJECT-TYPE
	SYNTAX      INTEGER {false(0), true(1)}
	MAX-ACCESS  read-only
	STATUS      current
	DESCRIPTION
		""
        ::= { amp6-Unit 2 }

amp6Unit-Failure    OBJECT-TYPE
	SYNTAX      INTEGER {false(0), true(1)}
	MAX-ACCESS  read-only
	STATUS      current
	DESCRIPTION
		""
        ::= { amp6-Unit 3 }

amp6Unit-Busy       OBJECT-TYPE
	SYNTAX      Integer32
	MAX-ACCESS  read-only
	STATUS      current
	DESCRIPTION
		""
        ::= { amp6-Unit 4 }

amp6Unit-Model      OBJECT-TYPE
	SYNTAX      OCTET STRING
	MAX-ACCESS  read-only
	STATUS      current
	DESCRIPTION
		""
        ::= { amp6-Unit 5 }

amp6Unit-Serial-Number OBJECT-TYPE
	SYNTAX      Integer32
	MAX-ACCESS  read-only
	STATUS      current
	DESCRIPTION
		""
        ::= { amp6-Unit 6 }

amp6Unit-Firmware-Version OBJECT-TYPE
	SYNTAX      OCTET STRING
	MAX-ACCESS  read-only
	STATUS      current
	DESCRIPTION
		""
        ::= { amp6-Unit 7 }

amp6Unit-Uptime     OBJECT-TYPE
	SYNTAX      DateAndTime
	MAX-ACCESS  read-only
	STATUS      current
	DESCRIPTION
		""
        ::= { amp6-Unit 8 }

amp6Unit-Post-Writes-Count OBJECT-TYPE
	SYNTAX      Integer32
	MAX-ACCESS  read-only
	STATUS      current
	DESCRIPTION
		""
        ::= { amp6-Unit 9 }

amp6Unit-IP-Address OBJECT-TYPE
	SYNTAX      IPAddress
	MAX-ACCESS  read-only
	STATUS      current
	DESCRIPTION
		""
        ::= { amp6-Unit 10 }

amp6Unit-TCP-Port   OBJECT-TYPE
	SYNTAX      Integer32
	MAX-ACCESS  read-only
	STATUS      current
	DESCRIPTION
		""
        ::= { amp6-Unit 11 }

amp6Unit-Adapter    OBJECT-TYPE
	SYNTAX      OCTET STRING
	MAX-ACCESS  read-only
	STATUS      current
	DESCRIPTION
		""
        ::= { amp6-Unit 12 }

amp6Unit-Reconnects OBJECT-TYPE
	SYNTAX      Integer32
	MAX-ACCESS  read-only
	STATUS      current
	DESCRIPTION
		""
        ::= { amp6-Unit 13 }

amp5DispCurs-Div-Current-Divider-1 OBJECT-TYPE
	SYNTAX      Integer32
	MAX-ACCESS  read-only
	STATUS      current
	DESCRIPTION
		""
        ::= { amp5Disp-Currents-Dividers 1 }

amp5DispCurs-Div-Current-Divider-2 OBJECT-TYPE
	SYNTAX      Integer32
	MAX-ACCESS  read-only
	STATUS      current
	DESCRIPTION
		""
        ::= { amp5Disp-Currents-Dividers 2 }

amp5DispCurs-Div-Current-Divider-3 OBJECT-TYPE
	SYNTAX      Integer32
	MAX-ACCESS  read-only
	STATUS      current
	DESCRIPTION
		""
        ::= { amp5Disp-Currents-Dividers 3 }

amp5DispCurs-Div-Current-Divider-4 OBJECT-TYPE
	SYNTAX      Integer32
	MAX-ACCESS  read-only
	STATUS      current
	DESCRIPTION
		""
        ::= { amp5Disp-Currents-Dividers 4 }

amp5DispCurs-Div-Current-Divider-5 OBJECT-TYPE
	SYNTAX      Integer32
	MAX-ACCESS  read-only
	STATUS      current
	DESCRIPTION
		""
        ::= { amp5Disp-Currents-Dividers 5 }

amp5DispCurs-Div-Current-Divider-6 OBJECT-TYPE
	SYNTAX      Integer32
	MAX-ACCESS  read-only
	STATUS      current
	DESCRIPTION
		""
        ::= { amp5Disp-Currents-Dividers 6 }

amp5DispCurs-Div-Current-Divider-7 OBJECT-TYPE
	SYNTAX      Integer32
	MAX-ACCESS  read-only
	STATUS      current
	DESCRIPTION
		""
        ::= { amp5Disp-Currents-Dividers 7 }

amp5DispCurs-Div-Current-Divider-8 OBJECT-TYPE
	SYNTAX      Integer32
	MAX-ACCESS  read-only
	STATUS      current
	DESCRIPTION
		""
        ::= { amp5Disp-Currents-Dividers 8 }

amp5DispCurs-Div-Current-Divider-9 OBJECT-TYPE
	SYNTAX      Integer32
	MAX-ACCESS  read-only
	STATUS      current
	DESCRIPTION
		""
        ::= { amp5Disp-Currents-Dividers 9 }

amp5DispCurs-Div-Current-Divider-10 OBJECT-TYPE
	SYNTAX      Integer32
	MAX-ACCESS  read-only
	STATUS      current
	DESCRIPTION
		""
        ::= { amp5Disp-Currents-Dividers 10 }

amp5DispCurs-Div-Current-Divider-11 OBJECT-TYPE
	SYNTAX      Integer32
	MAX-ACCESS  read-only
	STATUS      current
	DESCRIPTION
		""
        ::= { amp5Disp-Currents-Dividers 11 }

amp5DispCurs-Div-Current-Divider-12 OBJECT-TYPE
	SYNTAX      Integer32
	MAX-ACCESS  read-only
	STATUS      current
	DESCRIPTION
		""
        ::= { amp5Disp-Currents-Dividers 12 }

amp5DispCurs-Div-Current-Divider-13 OBJECT-TYPE
	SYNTAX      Integer32
	MAX-ACCESS  read-only
	STATUS      current
	DESCRIPTION
		""
        ::= { amp5Disp-Currents-Dividers 13 }

amp5DispCurs-Div-Current-Divider-14 OBJECT-TYPE
	SYNTAX      Integer32
	MAX-ACCESS  read-only
	STATUS      current
	DESCRIPTION
		""
        ::= { amp5Disp-Currents-Dividers 14 }

amp5DispCurs-Div-Current-Divider-15 OBJECT-TYPE
	SYNTAX      Integer32
	MAX-ACCESS  read-only
	STATUS      current
	DESCRIPTION
		""
        ::= { amp5Disp-Currents-Dividers 15 }

amp5DispCurs-Div-Current-Divider-16 OBJECT-TYPE
	SYNTAX      Integer32
	MAX-ACCESS  read-only
	STATUS      current
	DESCRIPTION
		""
        ::= { amp5Disp-Currents-Dividers 16 }

amp5DispCurs-Div-Current-Divider-17 OBJECT-TYPE
	SYNTAX      Integer32
	MAX-ACCESS  read-only
	STATUS      current
	DESCRIPTION
		""
        ::= { amp5Disp-Currents-Dividers 17 }

amp5DispCurs-Div-Current-Divider-18 OBJECT-TYPE
	SYNTAX      Integer32
	MAX-ACCESS  read-only
	STATUS      current
	DESCRIPTION
		""
        ::= { amp5Disp-Currents-Dividers 18 }

amp5DispCurs-Div-Current-Divider-19 OBJECT-TYPE
	SYNTAX      Integer32
	MAX-ACCESS  read-only
	STATUS      current
	DESCRIPTION
		""
        ::= { amp5Disp-Currents-Dividers 19 }

amp5DispCurs-Current-1 OBJECT-TYPE
	SYNTAX      Integer32
	MAX-ACCESS  read-only
	STATUS      current
	DESCRIPTION
		""
        ::= { amp5Disp-Currents 1 }

amp5DispCurs-Current-2 OBJECT-TYPE
	SYNTAX      Integer32
	MAX-ACCESS  read-only
	STATUS      current
	DESCRIPTION
		""
        ::= { amp5Disp-Currents 2 }

amp5DispCurs-Current-3 OBJECT-TYPE
	SYNTAX      Integer32
	MAX-ACCESS  read-only
	STATUS      current
	DESCRIPTION
		""
        ::= { amp5Disp-Currents 3 }

amp5DispCurs-Current-4 OBJECT-TYPE
	SYNTAX      Integer32
	MAX-ACCESS  read-only
	STATUS      current
	DESCRIPTION
		""
        ::= { amp5Disp-Currents 4 }

amp5DispCurs-Current-5 OBJECT-TYPE
	SYNTAX      Integer32
	MAX-ACCESS  read-only
	STATUS      current
	DESCRIPTION
		""
        ::= { amp5Disp-Currents 5 }

amp5DispCurs-Current-6 OBJECT-TYPE
	SYNTAX      Integer32
	MAX-ACCESS  read-only
	STATUS      current
	DESCRIPTION
		""
        ::= { amp5Disp-Currents 6 }

amp5DispCurs-Current-7 OBJECT-TYPE
	SYNTAX      Integer32
	MAX-ACCESS  read-only
	STATUS      current
	DESCRIPTION
		""
        ::= { amp5Disp-Currents 7 }

amp5DispCurs-Current-8 OBJECT-TYPE
	SYNTAX      Integer32
	MAX-ACCESS  read-only
	STATUS      current
	DESCRIPTION
		""
        ::= { amp5Disp-Currents 8 }

amp5DispCurs-Current-9 OBJECT-TYPE
	SYNTAX      Integer32
	MAX-ACCESS  read-only
	STATUS      current
	DESCRIPTION
		""
        ::= { amp5Disp-Currents 9 }

amp5DispCurs-Current-10 OBJECT-TYPE
	SYNTAX      Integer32
	MAX-ACCESS  read-only
	STATUS      current
	DESCRIPTION
		""
        ::= { amp5Disp-Currents 10 }

amp5DispCurs-Current-11 OBJECT-TYPE
	SYNTAX      Integer32
	MAX-ACCESS  read-only
	STATUS      current
	DESCRIPTION
		""
        ::= { amp5Disp-Currents 11 }

amp5DispCurs-Current-12 OBJECT-TYPE
	SYNTAX      Integer32
	MAX-ACCESS  read-only
	STATUS      current
	DESCRIPTION
		""
        ::= { amp5Disp-Currents 12 }

amp5DispCurs-Current-13 OBJECT-TYPE
	SYNTAX      Integer32
	MAX-ACCESS  read-only
	STATUS      current
	DESCRIPTION
		""
        ::= { amp5Disp-Currents 13 }

amp5DispCurs-Current-14 OBJECT-TYPE
	SYNTAX      Integer32
	MAX-ACCESS  read-only
	STATUS      current
	DESCRIPTION
		""
        ::= { amp5Disp-Currents 14 }

amp5DispCurs-Current-15 OBJECT-TYPE
	SYNTAX      Integer32
	MAX-ACCESS  read-only
	STATUS      current
	DESCRIPTION
		""
        ::= { amp5Disp-Currents 15 }

amp5DispCurs-Current-16 OBJECT-TYPE
	SYNTAX      Integer32
	MAX-ACCESS  read-only
	STATUS      current
	DESCRIPTION
		""
        ::= { amp5Disp-Currents 16 }

amp5DispCurs-Current-17 OBJECT-TYPE
	SYNTAX      Integer32
	MAX-ACCESS  read-only
	STATUS      current
	DESCRIPTION
		""
        ::= { amp5Disp-Currents 17 }

amp5DispCurs-Current-18 OBJECT-TYPE
	SYNTAX      Integer32
	MAX-ACCESS  read-only
	STATUS      current
	DESCRIPTION
		""
        ::= { amp5Disp-Currents 18 }

amp5DispCurs-Current-19 OBJECT-TYPE
	SYNTAX      Integer32
	MAX-ACCESS  read-only
	STATUS      current
	DESCRIPTION
		""
        ::= { amp5Disp-Currents 19 }

amp5DispTemps-Temperature-1 OBJECT-TYPE
	SYNTAX      Integer32
	MAX-ACCESS  read-only
	STATUS      current
	DESCRIPTION
		""
        ::= { amp5Disp-Temperatures 1 }

amp5DispTemps-Temperature-2 OBJECT-TYPE
	SYNTAX      Integer32
	MAX-ACCESS  read-only
	STATUS      current
	DESCRIPTION
		""
        ::= { amp5Disp-Temperatures 2 }

amp5DispMain-Status-Info OBJECT-TYPE
	SYNTAX      OCTET STRING
	MAX-ACCESS  read-only
	STATUS      current
	DESCRIPTION
		"Multiline, UTF8, separator: CRLF"
        ::= { amp5Disp-Main 1 }

amp5DispMain-Status-Warning OBJECT-TYPE
	SYNTAX      OCTET STRING
	MAX-ACCESS  read-only
	STATUS      current
	DESCRIPTION
		"Multiline, UTF8, separator: CRLF"
        ::= { amp5Disp-Main 2 }

amp5DispMain-Status-Failure OBJECT-TYPE
	SYNTAX      OCTET STRING
	MAX-ACCESS  read-only
	STATUS      current
	DESCRIPTION
		"Multiline, UTF8, separator: CRLF"
        ::= { amp5Disp-Main 3 }

amp5DispMain-Power-Out OBJECT-TYPE
	SYNTAX      Integer32
	MAX-ACCESS  read-only
	STATUS      current
	DESCRIPTION
		"Pout, unit: 0.1 W / 0.1 dB"
        ::= { amp5Disp-Main 4 }

amp5DispMain-Power-Average OBJECT-TYPE
	SYNTAX      Integer32
	MAX-ACCESS  read-only
	STATUS      current
	DESCRIPTION
		" PoutAvr, unit: 0.1 dB"
        ::= { amp5Disp-Main 5 }

amp5DispMain-Power-In OBJECT-TYPE
	SYNTAX      Integer32
	MAX-ACCESS  read-only
	STATUS      current
	DESCRIPTION
		"Pin, unit: 0.1 dB (-100000 = Unused)"
        ::= { amp5Disp-Main 6 }

amp5DispMain-Power-Ref OBJECT-TYPE
	SYNTAX      Integer32
	MAX-ACCESS  read-only
	STATUS      current
	DESCRIPTION
		"Pref, unit: 1/0.1/0.01 W / 1/0.1/0.01 dB, divider from ampXAux-PowerRef-Divider"
        ::= { amp5Disp-Main 7 }

amp5DispMain-Kp     OBJECT-TYPE
	SYNTAX      Integer32
	MAX-ACCESS  read-only
	STATUS      current
	DESCRIPTION
		"Kp, unit: 0.01 % (-100000 = Unused)"
        ::= { amp5Disp-Main 8 }

amp5DispMain-Phase  OBJECT-TYPE
	SYNTAX      Integer32
	MAX-ACCESS  read-only
	STATUS      current
	DESCRIPTION
		"Phase, unit: 0.1 % (-100000 = Unused)"
        ::= { amp5Disp-Main 9 }

amp5DispMain-dKp    OBJECT-TYPE
	SYNTAX      Integer32
	MAX-ACCESS  read-only
	STATUS      current
	DESCRIPTION
		"dKp, unit: 0.01 % (-100000 = Disabled)"
        ::= { amp5Disp-Main 10 }

amp5DispMain-Power-Out-2 OBJECT-TYPE
	SYNTAX      Integer32
	MAX-ACCESS  read-only
	STATUS      current
	DESCRIPTION
		"Pout2, unit: 1 W (-1 = Unused)"
        ::= { amp5Disp-Main 11 }

amp5DispMain-Profile OBJECT-TYPE
	SYNTAX      INTEGER {m1 (0), m2 (1)}
	MAX-ACCESS  read-only
	STATUS      current
	DESCRIPTION
		""
        ::= { amp5Disp-Main 12 }

amp5Aux-Status      OBJECT-TYPE
	SYNTAX      INTEGER {noFailure (0), powerOut (1), powerRef (2), powerIn (3), temperature1 (4), temperature2 (5), i1 (6), i2 (7), i3 (8), i4 (9), i5 (10), i6 (11), i7 (12), i8 (13), i9 (14), i10 (15), i11 (16), i12 (17), i13 (18), i14 (19), i15 (20), i16 (21), i17 (22), i18 (23), i19 (24), powerOutAvg (25), interErr (26), misc (31)}
	MAX-ACCESS  read-only
	STATUS      current
	DESCRIPTION
		"Amplifier internal failure status"
        ::= { amp5-Auxiliary 1 }

amp5Aux-Power-Units OBJECT-TYPE
	SYNTAX      INTEGER {none (0), watt (1), dB (2)}
	MAX-ACCESS  read-only
	STATUS      current
	DESCRIPTION
		"Amplifier Pout/Pref units: 1-W, 2-dB"
        ::= { amp5-Auxiliary 2 }

amp5Aux-Temperatures-Count OBJECT-TYPE
	SYNTAX      Integer32
	MAX-ACCESS  read-only
	STATUS      current
	DESCRIPTION
		"Temperatures sensors total count"
        ::= { amp5-Auxiliary 3 }

amp5Aux-Currents-Count OBJECT-TYPE
	SYNTAX      Integer32
	MAX-ACCESS  read-only
	STATUS      current
	DESCRIPTION
		"Currents sensors total count"
        ::= { amp5-Auxiliary 4 }

amp5Aux-Show-PowerOut-Only OBJECT-TYPE
	SYNTAX      INTEGER {false(0), true(1)}
	MAX-ACCESS  read-only
	STATUS      current
	DESCRIPTION
		"Display Pout only for main props: 0-No, 1-Yes"
        ::= { amp5-Auxiliary 5 }

amp5Aux-Show-PowerOut-Average OBJECT-TYPE
	SYNTAX      INTEGER {false(0), true(1)}
	MAX-ACCESS  read-only
	STATUS      current
	DESCRIPTION
		"Display Poutavg: 0-No, 1-Yes"
        ::= { amp5-Auxiliary 6 }

amp5Aux-Currents-Units OBJECT-TYPE
	SYNTAX      INTEGER {none (0), amper (1), percent (2)}
	MAX-ACCESS  read-only
	STATUS      current
	DESCRIPTION
		"Amplifier currents units: 1-Amperes (A), 2-Percent (%)"
        ::= { amp5-Auxiliary 7 }

amp5Aux-Show-dKp    OBJECT-TYPE
	SYNTAX      INTEGER {false(0), true(1)}
	MAX-ACCESS  read-only
	STATUS      current
	DESCRIPTION
		"Display dKp: 0-No, 1-Yes"
        ::= { amp5-Auxiliary 8 }

amp5Aux-PowerRef-Divider OBJECT-TYPE
	SYNTAX      Integer32
	MAX-ACCESS  read-only
	STATUS      current
	DESCRIPTION
		"Amplifier Pref divider: 1, 10, 100"
        ::= { amp5-Auxiliary 9 }

amp5Aux-Features    OBJECT-TYPE
	SYNTAX      Integer32
	MAX-ACCESS  read-only
	STATUS      current
	DESCRIPTION
		"Amplifier features/supports"
        ::= { amp5-Auxiliary 10 }

amp5Aux-Temperatures-Mapping OBJECT-TYPE
	SYNTAX      INTEGER {t1_T2 (0), tmax_Tps (1)}
	MAX-ACCESS  read-only
	STATUS      current
	DESCRIPTION
		"Temperatures titles mapping"
        ::= { amp5-Auxiliary 11 }

amp5Unit-Connected  OBJECT-TYPE
	SYNTAX      INTEGER {false(0), true(1)}
	MAX-ACCESS  read-only
	STATUS      current
	DESCRIPTION
		""
        ::= { amp5-Unit 1 }

amp5Unit-Warning    OBJECT-TYPE
	SYNTAX      INTEGER {false(0), true(1)}
	MAX-ACCESS  read-only
	STATUS      current
	DESCRIPTION
		""
        ::= { amp5-Unit 2 }

amp5Unit-Failure    OBJECT-TYPE
	SYNTAX      INTEGER {false(0), true(1)}
	MAX-ACCESS  read-only
	STATUS      current
	DESCRIPTION
		""
        ::= { amp5-Unit 3 }

amp5Unit-Busy       OBJECT-TYPE
	SYNTAX      Integer32
	MAX-ACCESS  read-only
	STATUS      current
	DESCRIPTION
		""
        ::= { amp5-Unit 4 }

amp5Unit-Model      OBJECT-TYPE
	SYNTAX      OCTET STRING
	MAX-ACCESS  read-only
	STATUS      current
	DESCRIPTION
		""
        ::= { amp5-Unit 5 }

amp5Unit-Serial-Number OBJECT-TYPE
	SYNTAX      Integer32
	MAX-ACCESS  read-only
	STATUS      current
	DESCRIPTION
		""
        ::= { amp5-Unit 6 }

amp5Unit-Firmware-Version OBJECT-TYPE
	SYNTAX      OCTET STRING
	MAX-ACCESS  read-only
	STATUS      current
	DESCRIPTION
		""
        ::= { amp5-Unit 7 }

amp5Unit-Uptime     OBJECT-TYPE
	SYNTAX      DateAndTime
	MAX-ACCESS  read-only
	STATUS      current
	DESCRIPTION
		""
        ::= { amp5-Unit 8 }

amp5Unit-Post-Writes-Count OBJECT-TYPE
	SYNTAX      Integer32
	MAX-ACCESS  read-only
	STATUS      current
	DESCRIPTION
		""
        ::= { amp5-Unit 9 }

amp5Unit-IP-Address OBJECT-TYPE
	SYNTAX      IPAddress
	MAX-ACCESS  read-only
	STATUS      current
	DESCRIPTION
		""
        ::= { amp5-Unit 10 }

amp5Unit-TCP-Port   OBJECT-TYPE
	SYNTAX      Integer32
	MAX-ACCESS  read-only
	STATUS      current
	DESCRIPTION
		""
        ::= { amp5-Unit 11 }

amp5Unit-Adapter    OBJECT-TYPE
	SYNTAX      OCTET STRING
	MAX-ACCESS  read-only
	STATUS      current
	DESCRIPTION
		""
        ::= { amp5-Unit 12 }

amp5Unit-Reconnects OBJECT-TYPE
	SYNTAX      Integer32
	MAX-ACCESS  read-only
	STATUS      current
	DESCRIPTION
		""
        ::= { amp5-Unit 13 }

amp4DispCurs-Div-Current-Divider-1 OBJECT-TYPE
	SYNTAX      Integer32
	MAX-ACCESS  read-only
	STATUS      current
	DESCRIPTION
		""
        ::= { amp4Disp-Currents-Dividers 1 }

amp4DispCurs-Div-Current-Divider-2 OBJECT-TYPE
	SYNTAX      Integer32
	MAX-ACCESS  read-only
	STATUS      current
	DESCRIPTION
		""
        ::= { amp4Disp-Currents-Dividers 2 }

amp4DispCurs-Div-Current-Divider-3 OBJECT-TYPE
	SYNTAX      Integer32
	MAX-ACCESS  read-only
	STATUS      current
	DESCRIPTION
		""
        ::= { amp4Disp-Currents-Dividers 3 }

amp4DispCurs-Div-Current-Divider-4 OBJECT-TYPE
	SYNTAX      Integer32
	MAX-ACCESS  read-only
	STATUS      current
	DESCRIPTION
		""
        ::= { amp4Disp-Currents-Dividers 4 }

amp4DispCurs-Div-Current-Divider-5 OBJECT-TYPE
	SYNTAX      Integer32
	MAX-ACCESS  read-only
	STATUS      current
	DESCRIPTION
		""
        ::= { amp4Disp-Currents-Dividers 5 }

amp4DispCurs-Div-Current-Divider-6 OBJECT-TYPE
	SYNTAX      Integer32
	MAX-ACCESS  read-only
	STATUS      current
	DESCRIPTION
		""
        ::= { amp4Disp-Currents-Dividers 6 }

amp4DispCurs-Div-Current-Divider-7 OBJECT-TYPE
	SYNTAX      Integer32
	MAX-ACCESS  read-only
	STATUS      current
	DESCRIPTION
		""
        ::= { amp4Disp-Currents-Dividers 7 }

amp4DispCurs-Div-Current-Divider-8 OBJECT-TYPE
	SYNTAX      Integer32
	MAX-ACCESS  read-only
	STATUS      current
	DESCRIPTION
		""
        ::= { amp4Disp-Currents-Dividers 8 }

amp4DispCurs-Div-Current-Divider-9 OBJECT-TYPE
	SYNTAX      Integer32
	MAX-ACCESS  read-only
	STATUS      current
	DESCRIPTION
		""
        ::= { amp4Disp-Currents-Dividers 9 }

amp4DispCurs-Div-Current-Divider-10 OBJECT-TYPE
	SYNTAX      Integer32
	MAX-ACCESS  read-only
	STATUS      current
	DESCRIPTION
		""
        ::= { amp4Disp-Currents-Dividers 10 }

amp4DispCurs-Div-Current-Divider-11 OBJECT-TYPE
	SYNTAX      Integer32
	MAX-ACCESS  read-only
	STATUS      current
	DESCRIPTION
		""
        ::= { amp4Disp-Currents-Dividers 11 }

amp4DispCurs-Div-Current-Divider-12 OBJECT-TYPE
	SYNTAX      Integer32
	MAX-ACCESS  read-only
	STATUS      current
	DESCRIPTION
		""
        ::= { amp4Disp-Currents-Dividers 12 }

amp4DispCurs-Div-Current-Divider-13 OBJECT-TYPE
	SYNTAX      Integer32
	MAX-ACCESS  read-only
	STATUS      current
	DESCRIPTION
		""
        ::= { amp4Disp-Currents-Dividers 13 }

amp4DispCurs-Div-Current-Divider-14 OBJECT-TYPE
	SYNTAX      Integer32
	MAX-ACCESS  read-only
	STATUS      current
	DESCRIPTION
		""
        ::= { amp4Disp-Currents-Dividers 14 }

amp4DispCurs-Div-Current-Divider-15 OBJECT-TYPE
	SYNTAX      Integer32
	MAX-ACCESS  read-only
	STATUS      current
	DESCRIPTION
		""
        ::= { amp4Disp-Currents-Dividers 15 }

amp4DispCurs-Div-Current-Divider-16 OBJECT-TYPE
	SYNTAX      Integer32
	MAX-ACCESS  read-only
	STATUS      current
	DESCRIPTION
		""
        ::= { amp4Disp-Currents-Dividers 16 }

amp4DispCurs-Div-Current-Divider-17 OBJECT-TYPE
	SYNTAX      Integer32
	MAX-ACCESS  read-only
	STATUS      current
	DESCRIPTION
		""
        ::= { amp4Disp-Currents-Dividers 17 }

amp4DispCurs-Div-Current-Divider-18 OBJECT-TYPE
	SYNTAX      Integer32
	MAX-ACCESS  read-only
	STATUS      current
	DESCRIPTION
		""
        ::= { amp4Disp-Currents-Dividers 18 }

amp4DispCurs-Div-Current-Divider-19 OBJECT-TYPE
	SYNTAX      Integer32
	MAX-ACCESS  read-only
	STATUS      current
	DESCRIPTION
		""
        ::= { amp4Disp-Currents-Dividers 19 }

amp4DispCurs-Current-1 OBJECT-TYPE
	SYNTAX      Integer32
	MAX-ACCESS  read-only
	STATUS      current
	DESCRIPTION
		""
        ::= { amp4Disp-Currents 1 }

amp4DispCurs-Current-2 OBJECT-TYPE
	SYNTAX      Integer32
	MAX-ACCESS  read-only
	STATUS      current
	DESCRIPTION
		""
        ::= { amp4Disp-Currents 2 }

amp4DispCurs-Current-3 OBJECT-TYPE
	SYNTAX      Integer32
	MAX-ACCESS  read-only
	STATUS      current
	DESCRIPTION
		""
        ::= { amp4Disp-Currents 3 }

amp4DispCurs-Current-4 OBJECT-TYPE
	SYNTAX      Integer32
	MAX-ACCESS  read-only
	STATUS      current
	DESCRIPTION
		""
        ::= { amp4Disp-Currents 4 }

amp4DispCurs-Current-5 OBJECT-TYPE
	SYNTAX      Integer32
	MAX-ACCESS  read-only
	STATUS      current
	DESCRIPTION
		""
        ::= { amp4Disp-Currents 5 }

amp4DispCurs-Current-6 OBJECT-TYPE
	SYNTAX      Integer32
	MAX-ACCESS  read-only
	STATUS      current
	DESCRIPTION
		""
        ::= { amp4Disp-Currents 6 }

amp4DispCurs-Current-7 OBJECT-TYPE
	SYNTAX      Integer32
	MAX-ACCESS  read-only
	STATUS      current
	DESCRIPTION
		""
        ::= { amp4Disp-Currents 7 }

amp4DispCurs-Current-8 OBJECT-TYPE
	SYNTAX      Integer32
	MAX-ACCESS  read-only
	STATUS      current
	DESCRIPTION
		""
        ::= { amp4Disp-Currents 8 }

amp4DispCurs-Current-9 OBJECT-TYPE
	SYNTAX      Integer32
	MAX-ACCESS  read-only
	STATUS      current
	DESCRIPTION
		""
        ::= { amp4Disp-Currents 9 }

amp4DispCurs-Current-10 OBJECT-TYPE
	SYNTAX      Integer32
	MAX-ACCESS  read-only
	STATUS      current
	DESCRIPTION
		""
        ::= { amp4Disp-Currents 10 }

amp4DispCurs-Current-11 OBJECT-TYPE
	SYNTAX      Integer32
	MAX-ACCESS  read-only
	STATUS      current
	DESCRIPTION
		""
        ::= { amp4Disp-Currents 11 }

amp4DispCurs-Current-12 OBJECT-TYPE
	SYNTAX      Integer32
	MAX-ACCESS  read-only
	STATUS      current
	DESCRIPTION
		""
        ::= { amp4Disp-Currents 12 }

amp4DispCurs-Current-13 OBJECT-TYPE
	SYNTAX      Integer32
	MAX-ACCESS  read-only
	STATUS      current
	DESCRIPTION
		""
        ::= { amp4Disp-Currents 13 }

amp4DispCurs-Current-14 OBJECT-TYPE
	SYNTAX      Integer32
	MAX-ACCESS  read-only
	STATUS      current
	DESCRIPTION
		""
        ::= { amp4Disp-Currents 14 }

amp4DispCurs-Current-15 OBJECT-TYPE
	SYNTAX      Integer32
	MAX-ACCESS  read-only
	STATUS      current
	DESCRIPTION
		""
        ::= { amp4Disp-Currents 15 }

amp4DispCurs-Current-16 OBJECT-TYPE
	SYNTAX      Integer32
	MAX-ACCESS  read-only
	STATUS      current
	DESCRIPTION
		""
        ::= { amp4Disp-Currents 16 }

amp4DispCurs-Current-17 OBJECT-TYPE
	SYNTAX      Integer32
	MAX-ACCESS  read-only
	STATUS      current
	DESCRIPTION
		""
        ::= { amp4Disp-Currents 17 }

amp4DispCurs-Current-18 OBJECT-TYPE
	SYNTAX      Integer32
	MAX-ACCESS  read-only
	STATUS      current
	DESCRIPTION
		""
        ::= { amp4Disp-Currents 18 }

amp4DispCurs-Current-19 OBJECT-TYPE
	SYNTAX      Integer32
	MAX-ACCESS  read-only
	STATUS      current
	DESCRIPTION
		""
        ::= { amp4Disp-Currents 19 }

amp4DispTemps-Temperature-1 OBJECT-TYPE
	SYNTAX      Integer32
	MAX-ACCESS  read-only
	STATUS      current
	DESCRIPTION
		""
        ::= { amp4Disp-Temperatures 1 }

amp4DispTemps-Temperature-2 OBJECT-TYPE
	SYNTAX      Integer32
	MAX-ACCESS  read-only
	STATUS      current
	DESCRIPTION
		""
        ::= { amp4Disp-Temperatures 2 }

amp4DispMain-Status-Info OBJECT-TYPE
	SYNTAX      OCTET STRING
	MAX-ACCESS  read-only
	STATUS      current
	DESCRIPTION
		"Multiline, UTF8, separator: CRLF"
        ::= { amp4Disp-Main 1 }

amp4DispMain-Status-Warning OBJECT-TYPE
	SYNTAX      OCTET STRING
	MAX-ACCESS  read-only
	STATUS      current
	DESCRIPTION
		"Multiline, UTF8, separator: CRLF"
        ::= { amp4Disp-Main 2 }

amp4DispMain-Status-Failure OBJECT-TYPE
	SYNTAX      OCTET STRING
	MAX-ACCESS  read-only
	STATUS      current
	DESCRIPTION
		"Multiline, UTF8, separator: CRLF"
        ::= { amp4Disp-Main 3 }

amp4DispMain-Power-Out OBJECT-TYPE
	SYNTAX      Integer32
	MAX-ACCESS  read-only
	STATUS      current
	DESCRIPTION
		"Pout, unit: 0.1 W / 0.1 dB"
        ::= { amp4Disp-Main 4 }

amp4DispMain-Power-Average OBJECT-TYPE
	SYNTAX      Integer32
	MAX-ACCESS  read-only
	STATUS      current
	DESCRIPTION
		" PoutAvr, unit: 0.1 dB"
        ::= { amp4Disp-Main 5 }

amp4DispMain-Power-In OBJECT-TYPE
	SYNTAX      Integer32
	MAX-ACCESS  read-only
	STATUS      current
	DESCRIPTION
		"Pin, unit: 0.1 dB (-100000 = Unused)"
        ::= { amp4Disp-Main 6 }

amp4DispMain-Power-Ref OBJECT-TYPE
	SYNTAX      Integer32
	MAX-ACCESS  read-only
	STATUS      current
	DESCRIPTION
		"Pref, unit: 1/0.1/0.01 W / 1/0.1/0.01 dB, divider from ampXAux-PowerRef-Divider"
        ::= { amp4Disp-Main 7 }

amp4DispMain-Kp     OBJECT-TYPE
	SYNTAX      Integer32
	MAX-ACCESS  read-only
	STATUS      current
	DESCRIPTION
		"Kp, unit: 0.01 % (-100000 = Unused)"
        ::= { amp4Disp-Main 8 }

amp4DispMain-Phase  OBJECT-TYPE
	SYNTAX      Integer32
	MAX-ACCESS  read-only
	STATUS      current
	DESCRIPTION
		"Phase, unit: 0.1 % (-100000 = Unused)"
        ::= { amp4Disp-Main 9 }

amp4DispMain-dKp    OBJECT-TYPE
	SYNTAX      Integer32
	MAX-ACCESS  read-only
	STATUS      current
	DESCRIPTION
		"dKp, unit: 0.01 % (-100000 = Disabled)"
        ::= { amp4Disp-Main 10 }

amp4DispMain-Power-Out-2 OBJECT-TYPE
	SYNTAX      Integer32
	MAX-ACCESS  read-only
	STATUS      current
	DESCRIPTION
		"Pout2, unit: 1 W (-1 = Unused)"
        ::= { amp4Disp-Main 11 }

amp4DispMain-Profile OBJECT-TYPE
	SYNTAX      INTEGER {m1 (0), m2 (1)}
	MAX-ACCESS  read-only
	STATUS      current
	DESCRIPTION
		""
        ::= { amp4Disp-Main 12 }

amp4Aux-Status      OBJECT-TYPE
	SYNTAX      INTEGER {noFailure (0), powerOut (1), powerRef (2), powerIn (3), temperature1 (4), temperature2 (5), i1 (6), i2 (7), i3 (8), i4 (9), i5 (10), i6 (11), i7 (12), i8 (13), i9 (14), i10 (15), i11 (16), i12 (17), i13 (18), i14 (19), i15 (20), i16 (21), i17 (22), i18 (23), i19 (24), powerOutAvg (25), interErr (26), misc (31)}
	MAX-ACCESS  read-only
	STATUS      current
	DESCRIPTION
		"Amplifier internal failure status"
        ::= { amp4-Auxiliary 1 }

amp4Aux-Power-Units OBJECT-TYPE
	SYNTAX      INTEGER {none (0), watt (1), dB (2)}
	MAX-ACCESS  read-only
	STATUS      current
	DESCRIPTION
		"Amplifier Pout/Pref units: 1-W, 2-dB"
        ::= { amp4-Auxiliary 2 }

amp4Aux-Temperatures-Count OBJECT-TYPE
	SYNTAX      Integer32
	MAX-ACCESS  read-only
	STATUS      current
	DESCRIPTION
		"Temperatures sensors total count"
        ::= { amp4-Auxiliary 3 }

amp4Aux-Currents-Count OBJECT-TYPE
	SYNTAX      Integer32
	MAX-ACCESS  read-only
	STATUS      current
	DESCRIPTION
		"Currents sensors total count"
        ::= { amp4-Auxiliary 4 }

amp4Aux-Show-PowerOut-Only OBJECT-TYPE
	SYNTAX      INTEGER {false(0), true(1)}
	MAX-ACCESS  read-only
	STATUS      current
	DESCRIPTION
		"Display Pout only for main props: 0-No, 1-Yes"
        ::= { amp4-Auxiliary 5 }

amp4Aux-Show-PowerOut-Average OBJECT-TYPE
	SYNTAX      INTEGER {false(0), true(1)}
	MAX-ACCESS  read-only
	STATUS      current
	DESCRIPTION
		"Display Poutavg: 0-No, 1-Yes"
        ::= { amp4-Auxiliary 6 }

amp4Aux-Currents-Units OBJECT-TYPE
	SYNTAX      INTEGER {none (0), amper (1), percent (2)}
	MAX-ACCESS  read-only
	STATUS      current
	DESCRIPTION
		"Amplifier currents units: 1-Amperes (A), 2-Percent (%)"
        ::= { amp4-Auxiliary 7 }

amp4Aux-Show-dKp    OBJECT-TYPE
	SYNTAX      INTEGER {false(0), true(1)}
	MAX-ACCESS  read-only
	STATUS      current
	DESCRIPTION
		"Display dKp: 0-No, 1-Yes"
        ::= { amp4-Auxiliary 8 }

amp4Aux-PowerRef-Divider OBJECT-TYPE
	SYNTAX      Integer32
	MAX-ACCESS  read-only
	STATUS      current
	DESCRIPTION
		"Amplifier Pref divider: 1, 10, 100"
        ::= { amp4-Auxiliary 9 }

amp4Aux-Features    OBJECT-TYPE
	SYNTAX      Integer32
	MAX-ACCESS  read-only
	STATUS      current
	DESCRIPTION
		"Amplifier features/supports"
        ::= { amp4-Auxiliary 10 }

amp4Aux-Temperatures-Mapping OBJECT-TYPE
	SYNTAX      INTEGER {t1_T2 (0), tmax_Tps (1)}
	MAX-ACCESS  read-only
	STATUS      current
	DESCRIPTION
		"Temperatures titles mapping"
        ::= { amp4-Auxiliary 11 }

amp4Unit-Connected  OBJECT-TYPE
	SYNTAX      INTEGER {false(0), true(1)}
	MAX-ACCESS  read-only
	STATUS      current
	DESCRIPTION
		""
        ::= { amp4-Unit 1 }

amp4Unit-Warning    OBJECT-TYPE
	SYNTAX      INTEGER {false(0), true(1)}
	MAX-ACCESS  read-only
	STATUS      current
	DESCRIPTION
		""
        ::= { amp4-Unit 2 }

amp4Unit-Failure    OBJECT-TYPE
	SYNTAX      INTEGER {false(0), true(1)}
	MAX-ACCESS  read-only
	STATUS      current
	DESCRIPTION
		""
        ::= { amp4-Unit 3 }

amp4Unit-Busy       OBJECT-TYPE
	SYNTAX      Integer32
	MAX-ACCESS  read-only
	STATUS      current
	DESCRIPTION
		""
        ::= { amp4-Unit 4 }

amp4Unit-Model      OBJECT-TYPE
	SYNTAX      OCTET STRING
	MAX-ACCESS  read-only
	STATUS      current
	DESCRIPTION
		""
        ::= { amp4-Unit 5 }

amp4Unit-Serial-Number OBJECT-TYPE
	SYNTAX      Integer32
	MAX-ACCESS  read-only
	STATUS      current
	DESCRIPTION
		""
        ::= { amp4-Unit 6 }

amp4Unit-Firmware-Version OBJECT-TYPE
	SYNTAX      OCTET STRING
	MAX-ACCESS  read-only
	STATUS      current
	DESCRIPTION
		""
        ::= { amp4-Unit 7 }

amp4Unit-Uptime     OBJECT-TYPE
	SYNTAX      DateAndTime
	MAX-ACCESS  read-only
	STATUS      current
	DESCRIPTION
		""
        ::= { amp4-Unit 8 }

amp4Unit-Post-Writes-Count OBJECT-TYPE
	SYNTAX      Integer32
	MAX-ACCESS  read-only
	STATUS      current
	DESCRIPTION
		""
        ::= { amp4-Unit 9 }

amp4Unit-IP-Address OBJECT-TYPE
	SYNTAX      IPAddress
	MAX-ACCESS  read-only
	STATUS      current
	DESCRIPTION
		""
        ::= { amp4-Unit 10 }

amp4Unit-TCP-Port   OBJECT-TYPE
	SYNTAX      Integer32
	MAX-ACCESS  read-only
	STATUS      current
	DESCRIPTION
		""
        ::= { amp4-Unit 11 }

amp4Unit-Adapter    OBJECT-TYPE
	SYNTAX      OCTET STRING
	MAX-ACCESS  read-only
	STATUS      current
	DESCRIPTION
		""
        ::= { amp4-Unit 12 }

amp4Unit-Reconnects OBJECT-TYPE
	SYNTAX      Integer32
	MAX-ACCESS  read-only
	STATUS      current
	DESCRIPTION
		""
        ::= { amp4-Unit 13 }

amp3DispCurs-Div-Current-Divider-1 OBJECT-TYPE
	SYNTAX      Integer32
	MAX-ACCESS  read-only
	STATUS      current
	DESCRIPTION
		""
        ::= { amp3Disp-Currents-Dividers 1 }

amp3DispCurs-Div-Current-Divider-2 OBJECT-TYPE
	SYNTAX      Integer32
	MAX-ACCESS  read-only
	STATUS      current
	DESCRIPTION
		""
        ::= { amp3Disp-Currents-Dividers 2 }

amp3DispCurs-Div-Current-Divider-3 OBJECT-TYPE
	SYNTAX      Integer32
	MAX-ACCESS  read-only
	STATUS      current
	DESCRIPTION
		""
        ::= { amp3Disp-Currents-Dividers 3 }

amp3DispCurs-Div-Current-Divider-4 OBJECT-TYPE
	SYNTAX      Integer32
	MAX-ACCESS  read-only
	STATUS      current
	DESCRIPTION
		""
        ::= { amp3Disp-Currents-Dividers 4 }

amp3DispCurs-Div-Current-Divider-5 OBJECT-TYPE
	SYNTAX      Integer32
	MAX-ACCESS  read-only
	STATUS      current
	DESCRIPTION
		""
        ::= { amp3Disp-Currents-Dividers 5 }

amp3DispCurs-Div-Current-Divider-6 OBJECT-TYPE
	SYNTAX      Integer32
	MAX-ACCESS  read-only
	STATUS      current
	DESCRIPTION
		""
        ::= { amp3Disp-Currents-Dividers 6 }

amp3DispCurs-Div-Current-Divider-7 OBJECT-TYPE
	SYNTAX      Integer32
	MAX-ACCESS  read-only
	STATUS      current
	DESCRIPTION
		""
        ::= { amp3Disp-Currents-Dividers 7 }

amp3DispCurs-Div-Current-Divider-8 OBJECT-TYPE
	SYNTAX      Integer32
	MAX-ACCESS  read-only
	STATUS      current
	DESCRIPTION
		""
        ::= { amp3Disp-Currents-Dividers 8 }

amp3DispCurs-Div-Current-Divider-9 OBJECT-TYPE
	SYNTAX      Integer32
	MAX-ACCESS  read-only
	STATUS      current
	DESCRIPTION
		""
        ::= { amp3Disp-Currents-Dividers 9 }

amp3DispCurs-Div-Current-Divider-10 OBJECT-TYPE
	SYNTAX      Integer32
	MAX-ACCESS  read-only
	STATUS      current
	DESCRIPTION
		""
        ::= { amp3Disp-Currents-Dividers 10 }

amp3DispCurs-Div-Current-Divider-11 OBJECT-TYPE
	SYNTAX      Integer32
	MAX-ACCESS  read-only
	STATUS      current
	DESCRIPTION
		""
        ::= { amp3Disp-Currents-Dividers 11 }

amp3DispCurs-Div-Current-Divider-12 OBJECT-TYPE
	SYNTAX      Integer32
	MAX-ACCESS  read-only
	STATUS      current
	DESCRIPTION
		""
        ::= { amp3Disp-Currents-Dividers 12 }

amp3DispCurs-Div-Current-Divider-13 OBJECT-TYPE
	SYNTAX      Integer32
	MAX-ACCESS  read-only
	STATUS      current
	DESCRIPTION
		""
        ::= { amp3Disp-Currents-Dividers 13 }

amp3DispCurs-Div-Current-Divider-14 OBJECT-TYPE
	SYNTAX      Integer32
	MAX-ACCESS  read-only
	STATUS      current
	DESCRIPTION
		""
        ::= { amp3Disp-Currents-Dividers 14 }

amp3DispCurs-Div-Current-Divider-15 OBJECT-TYPE
	SYNTAX      Integer32
	MAX-ACCESS  read-only
	STATUS      current
	DESCRIPTION
		""
        ::= { amp3Disp-Currents-Dividers 15 }

amp3DispCurs-Div-Current-Divider-16 OBJECT-TYPE
	SYNTAX      Integer32
	MAX-ACCESS  read-only
	STATUS      current
	DESCRIPTION
		""
        ::= { amp3Disp-Currents-Dividers 16 }

amp3DispCurs-Div-Current-Divider-17 OBJECT-TYPE
	SYNTAX      Integer32
	MAX-ACCESS  read-only
	STATUS      current
	DESCRIPTION
		""
        ::= { amp3Disp-Currents-Dividers 17 }

amp3DispCurs-Div-Current-Divider-18 OBJECT-TYPE
	SYNTAX      Integer32
	MAX-ACCESS  read-only
	STATUS      current
	DESCRIPTION
		""
        ::= { amp3Disp-Currents-Dividers 18 }

amp3DispCurs-Div-Current-Divider-19 OBJECT-TYPE
	SYNTAX      Integer32
	MAX-ACCESS  read-only
	STATUS      current
	DESCRIPTION
		""
        ::= { amp3Disp-Currents-Dividers 19 }

amp3DispCurs-Current-1 OBJECT-TYPE
	SYNTAX      Integer32
	MAX-ACCESS  read-only
	STATUS      current
	DESCRIPTION
		""
        ::= { amp3Disp-Currents 1 }

amp3DispCurs-Current-2 OBJECT-TYPE
	SYNTAX      Integer32
	MAX-ACCESS  read-only
	STATUS      current
	DESCRIPTION
		""
        ::= { amp3Disp-Currents 2 }

amp3DispCurs-Current-3 OBJECT-TYPE
	SYNTAX      Integer32
	MAX-ACCESS  read-only
	STATUS      current
	DESCRIPTION
		""
        ::= { amp3Disp-Currents 3 }

amp3DispCurs-Current-4 OBJECT-TYPE
	SYNTAX      Integer32
	MAX-ACCESS  read-only
	STATUS      current
	DESCRIPTION
		""
        ::= { amp3Disp-Currents 4 }

amp3DispCurs-Current-5 OBJECT-TYPE
	SYNTAX      Integer32
	MAX-ACCESS  read-only
	STATUS      current
	DESCRIPTION
		""
        ::= { amp3Disp-Currents 5 }

amp3DispCurs-Current-6 OBJECT-TYPE
	SYNTAX      Integer32
	MAX-ACCESS  read-only
	STATUS      current
	DESCRIPTION
		""
        ::= { amp3Disp-Currents 6 }

amp3DispCurs-Current-7 OBJECT-TYPE
	SYNTAX      Integer32
	MAX-ACCESS  read-only
	STATUS      current
	DESCRIPTION
		""
        ::= { amp3Disp-Currents 7 }

amp3DispCurs-Current-8 OBJECT-TYPE
	SYNTAX      Integer32
	MAX-ACCESS  read-only
	STATUS      current
	DESCRIPTION
		""
        ::= { amp3Disp-Currents 8 }

amp3DispCurs-Current-9 OBJECT-TYPE
	SYNTAX      Integer32
	MAX-ACCESS  read-only
	STATUS      current
	DESCRIPTION
		""
        ::= { amp3Disp-Currents 9 }

amp3DispCurs-Current-10 OBJECT-TYPE
	SYNTAX      Integer32
	MAX-ACCESS  read-only
	STATUS      current
	DESCRIPTION
		""
        ::= { amp3Disp-Currents 10 }

amp3DispCurs-Current-11 OBJECT-TYPE
	SYNTAX      Integer32
	MAX-ACCESS  read-only
	STATUS      current
	DESCRIPTION
		""
        ::= { amp3Disp-Currents 11 }

amp3DispCurs-Current-12 OBJECT-TYPE
	SYNTAX      Integer32
	MAX-ACCESS  read-only
	STATUS      current
	DESCRIPTION
		""
        ::= { amp3Disp-Currents 12 }

amp3DispCurs-Current-13 OBJECT-TYPE
	SYNTAX      Integer32
	MAX-ACCESS  read-only
	STATUS      current
	DESCRIPTION
		""
        ::= { amp3Disp-Currents 13 }

amp3DispCurs-Current-14 OBJECT-TYPE
	SYNTAX      Integer32
	MAX-ACCESS  read-only
	STATUS      current
	DESCRIPTION
		""
        ::= { amp3Disp-Currents 14 }

amp3DispCurs-Current-15 OBJECT-TYPE
	SYNTAX      Integer32
	MAX-ACCESS  read-only
	STATUS      current
	DESCRIPTION
		""
        ::= { amp3Disp-Currents 15 }

amp3DispCurs-Current-16 OBJECT-TYPE
	SYNTAX      Integer32
	MAX-ACCESS  read-only
	STATUS      current
	DESCRIPTION
		""
        ::= { amp3Disp-Currents 16 }

amp3DispCurs-Current-17 OBJECT-TYPE
	SYNTAX      Integer32
	MAX-ACCESS  read-only
	STATUS      current
	DESCRIPTION
		""
        ::= { amp3Disp-Currents 17 }

amp3DispCurs-Current-18 OBJECT-TYPE
	SYNTAX      Integer32
	MAX-ACCESS  read-only
	STATUS      current
	DESCRIPTION
		""
        ::= { amp3Disp-Currents 18 }

amp3DispCurs-Current-19 OBJECT-TYPE
	SYNTAX      Integer32
	MAX-ACCESS  read-only
	STATUS      current
	DESCRIPTION
		""
        ::= { amp3Disp-Currents 19 }

amp3DispTemps-Temperature-1 OBJECT-TYPE
	SYNTAX      Integer32
	MAX-ACCESS  read-only
	STATUS      current
	DESCRIPTION
		""
        ::= { amp3Disp-Temperatures 1 }

amp3DispTemps-Temperature-2 OBJECT-TYPE
	SYNTAX      Integer32
	MAX-ACCESS  read-only
	STATUS      current
	DESCRIPTION
		""
        ::= { amp3Disp-Temperatures 2 }

amp3DispMain-Status-Info OBJECT-TYPE
	SYNTAX      OCTET STRING
	MAX-ACCESS  read-only
	STATUS      current
	DESCRIPTION
		"Multiline, UTF8, separator: CRLF"
        ::= { amp3Disp-Main 1 }

amp3DispMain-Status-Warning OBJECT-TYPE
	SYNTAX      OCTET STRING
	MAX-ACCESS  read-only
	STATUS      current
	DESCRIPTION
		"Multiline, UTF8, separator: CRLF"
        ::= { amp3Disp-Main 2 }

amp3DispMain-Status-Failure OBJECT-TYPE
	SYNTAX      OCTET STRING
	MAX-ACCESS  read-only
	STATUS      current
	DESCRIPTION
		"Multiline, UTF8, separator: CRLF"
        ::= { amp3Disp-Main 3 }

amp3DispMain-Power-Out OBJECT-TYPE
	SYNTAX      Integer32
	MAX-ACCESS  read-only
	STATUS      current
	DESCRIPTION
		"Pout, unit: 0.1 W / 0.1 dB"
        ::= { amp3Disp-Main 4 }

amp3DispMain-Power-Average OBJECT-TYPE
	SYNTAX      Integer32
	MAX-ACCESS  read-only
	STATUS      current
	DESCRIPTION
		" PoutAvr, unit: 0.1 dB"
        ::= { amp3Disp-Main 5 }

amp3DispMain-Power-In OBJECT-TYPE
	SYNTAX      Integer32
	MAX-ACCESS  read-only
	STATUS      current
	DESCRIPTION
		"Pin, unit: 0.1 dB (-100000 = Unused)"
        ::= { amp3Disp-Main 6 }

amp3DispMain-Power-Ref OBJECT-TYPE
	SYNTAX      Integer32
	MAX-ACCESS  read-only
	STATUS      current
	DESCRIPTION
		"Pref, unit: 1/0.1/0.01 W / 1/0.1/0.01 dB, divider from ampXAux-PowerRef-Divider"
        ::= { amp3Disp-Main 7 }

amp3DispMain-Kp     OBJECT-TYPE
	SYNTAX      Integer32
	MAX-ACCESS  read-only
	STATUS      current
	DESCRIPTION
		"Kp, unit: 0.01 % (-100000 = Unused)"
        ::= { amp3Disp-Main 8 }

amp3DispMain-Phase  OBJECT-TYPE
	SYNTAX      Integer32
	MAX-ACCESS  read-only
	STATUS      current
	DESCRIPTION
		"Phase, unit: 0.1 % (-100000 = Unused)"
        ::= { amp3Disp-Main 9 }

amp3DispMain-dKp    OBJECT-TYPE
	SYNTAX      Integer32
	MAX-ACCESS  read-only
	STATUS      current
	DESCRIPTION
		"dKp, unit: 0.01 % (-100000 = Disabled)"
        ::= { amp3Disp-Main 10 }

amp3DispMain-Power-Out-2 OBJECT-TYPE
	SYNTAX      Integer32
	MAX-ACCESS  read-only
	STATUS      current
	DESCRIPTION
		"Pout2, unit: 1 W (-1 = Unused)"
        ::= { amp3Disp-Main 11 }

amp3DispMain-Profile OBJECT-TYPE
	SYNTAX      INTEGER {m1 (0), m2 (1)}
	MAX-ACCESS  read-only
	STATUS      current
	DESCRIPTION
		""
        ::= { amp3Disp-Main 12 }

amp3Aux-Status      OBJECT-TYPE
	SYNTAX      INTEGER {noFailure (0), powerOut (1), powerRef (2), powerIn (3), temperature1 (4), temperature2 (5), i1 (6), i2 (7), i3 (8), i4 (9), i5 (10), i6 (11), i7 (12), i8 (13), i9 (14), i10 (15), i11 (16), i12 (17), i13 (18), i14 (19), i15 (20), i16 (21), i17 (22), i18 (23), i19 (24), powerOutAvg (25), interErr (26), misc (31)}
	MAX-ACCESS  read-only
	STATUS      current
	DESCRIPTION
		"Amplifier internal failure status"
        ::= { amp3-Auxiliary 1 }

amp3Aux-Power-Units OBJECT-TYPE
	SYNTAX      INTEGER {none (0), watt (1), dB (2)}
	MAX-ACCESS  read-only
	STATUS      current
	DESCRIPTION
		"Amplifier Pout/Pref units: 1-W, 2-dB"
        ::= { amp3-Auxiliary 2 }

amp3Aux-Temperatures-Count OBJECT-TYPE
	SYNTAX      Integer32
	MAX-ACCESS  read-only
	STATUS      current
	DESCRIPTION
		"Temperatures sensors total count"
        ::= { amp3-Auxiliary 3 }

amp3Aux-Currents-Count OBJECT-TYPE
	SYNTAX      Integer32
	MAX-ACCESS  read-only
	STATUS      current
	DESCRIPTION
		"Currents sensors total count"
        ::= { amp3-Auxiliary 4 }

amp3Aux-Show-PowerOut-Only OBJECT-TYPE
	SYNTAX      INTEGER {false(0), true(1)}
	MAX-ACCESS  read-only
	STATUS      current
	DESCRIPTION
		"Display Pout only for main props: 0-No, 1-Yes"
        ::= { amp3-Auxiliary 5 }

amp3Aux-Show-PowerOut-Average OBJECT-TYPE
	SYNTAX      INTEGER {false(0), true(1)}
	MAX-ACCESS  read-only
	STATUS      current
	DESCRIPTION
		"Display Poutavg: 0-No, 1-Yes"
        ::= { amp3-Auxiliary 6 }

amp3Aux-Currents-Units OBJECT-TYPE
	SYNTAX      INTEGER {none (0), amper (1), percent (2)}
	MAX-ACCESS  read-only
	STATUS      current
	DESCRIPTION
		"Amplifier currents units: 1-Amperes (A), 2-Percent (%)"
        ::= { amp3-Auxiliary 7 }

amp3Aux-Show-dKp    OBJECT-TYPE
	SYNTAX      INTEGER {false(0), true(1)}
	MAX-ACCESS  read-only
	STATUS      current
	DESCRIPTION
		"Display dKp: 0-No, 1-Yes"
        ::= { amp3-Auxiliary 8 }

amp3Aux-PowerRef-Divider OBJECT-TYPE
	SYNTAX      Integer32
	MAX-ACCESS  read-only
	STATUS      current
	DESCRIPTION
		"Amplifier Pref divider: 1, 10, 100"
        ::= { amp3-Auxiliary 9 }

amp3Aux-Features    OBJECT-TYPE
	SYNTAX      Integer32
	MAX-ACCESS  read-only
	STATUS      current
	DESCRIPTION
		"Amplifier features/supports"
        ::= { amp3-Auxiliary 10 }

amp3Aux-Temperatures-Mapping OBJECT-TYPE
	SYNTAX      INTEGER {t1_T2 (0), tmax_Tps (1)}
	MAX-ACCESS  read-only
	STATUS      current
	DESCRIPTION
		"Temperatures titles mapping"
        ::= { amp3-Auxiliary 11 }

amp3Unit-Connected  OBJECT-TYPE
	SYNTAX      INTEGER {false(0), true(1)}
	MAX-ACCESS  read-only
	STATUS      current
	DESCRIPTION
		""
        ::= { amp3-Unit 1 }

amp3Unit-Warning    OBJECT-TYPE
	SYNTAX      INTEGER {false(0), true(1)}
	MAX-ACCESS  read-only
	STATUS      current
	DESCRIPTION
		""
        ::= { amp3-Unit 2 }

amp3Unit-Failure    OBJECT-TYPE
	SYNTAX      INTEGER {false(0), true(1)}
	MAX-ACCESS  read-only
	STATUS      current
	DESCRIPTION
		""
        ::= { amp3-Unit 3 }

amp3Unit-Busy       OBJECT-TYPE
	SYNTAX      Integer32
	MAX-ACCESS  read-only
	STATUS      current
	DESCRIPTION
		""
        ::= { amp3-Unit 4 }

amp3Unit-Model      OBJECT-TYPE
	SYNTAX      OCTET STRING
	MAX-ACCESS  read-only
	STATUS      current
	DESCRIPTION
		""
        ::= { amp3-Unit 5 }

amp3Unit-Serial-Number OBJECT-TYPE
	SYNTAX      Integer32
	MAX-ACCESS  read-only
	STATUS      current
	DESCRIPTION
		""
        ::= { amp3-Unit 6 }

amp3Unit-Firmware-Version OBJECT-TYPE
	SYNTAX      OCTET STRING
	MAX-ACCESS  read-only
	STATUS      current
	DESCRIPTION
		""
        ::= { amp3-Unit 7 }

amp3Unit-Uptime     OBJECT-TYPE
	SYNTAX      DateAndTime
	MAX-ACCESS  read-only
	STATUS      current
	DESCRIPTION
		""
        ::= { amp3-Unit 8 }

amp3Unit-Post-Writes-Count OBJECT-TYPE
	SYNTAX      Integer32
	MAX-ACCESS  read-only
	STATUS      current
	DESCRIPTION
		""
        ::= { amp3-Unit 9 }

amp3Unit-IP-Address OBJECT-TYPE
	SYNTAX      IPAddress
	MAX-ACCESS  read-only
	STATUS      current
	DESCRIPTION
		""
        ::= { amp3-Unit 10 }

amp3Unit-TCP-Port   OBJECT-TYPE
	SYNTAX      Integer32
	MAX-ACCESS  read-only
	STATUS      current
	DESCRIPTION
		""
        ::= { amp3-Unit 11 }

amp3Unit-Adapter    OBJECT-TYPE
	SYNTAX      OCTET STRING
	MAX-ACCESS  read-only
	STATUS      current
	DESCRIPTION
		""
        ::= { amp3-Unit 12 }

amp3Unit-Reconnects OBJECT-TYPE
	SYNTAX      Integer32
	MAX-ACCESS  read-only
	STATUS      current
	DESCRIPTION
		""
        ::= { amp3-Unit 13 }

amp2DispCurs-Div-Current-Divider-1 OBJECT-TYPE
	SYNTAX      Integer32
	MAX-ACCESS  read-only
	STATUS      current
	DESCRIPTION
		""
        ::= { amp2Disp-Currents-Dividers 1 }

amp2DispCurs-Div-Current-Divider-2 OBJECT-TYPE
	SYNTAX      Integer32
	MAX-ACCESS  read-only
	STATUS      current
	DESCRIPTION
		""
        ::= { amp2Disp-Currents-Dividers 2 }

amp2DispCurs-Div-Current-Divider-3 OBJECT-TYPE
	SYNTAX      Integer32
	MAX-ACCESS  read-only
	STATUS      current
	DESCRIPTION
		""
        ::= { amp2Disp-Currents-Dividers 3 }

amp2DispCurs-Div-Current-Divider-4 OBJECT-TYPE
	SYNTAX      Integer32
	MAX-ACCESS  read-only
	STATUS      current
	DESCRIPTION
		""
        ::= { amp2Disp-Currents-Dividers 4 }

amp2DispCurs-Div-Current-Divider-5 OBJECT-TYPE
	SYNTAX      Integer32
	MAX-ACCESS  read-only
	STATUS      current
	DESCRIPTION
		""
        ::= { amp2Disp-Currents-Dividers 5 }

amp2DispCurs-Div-Current-Divider-6 OBJECT-TYPE
	SYNTAX      Integer32
	MAX-ACCESS  read-only
	STATUS      current
	DESCRIPTION
		""
        ::= { amp2Disp-Currents-Dividers 6 }

amp2DispCurs-Div-Current-Divider-7 OBJECT-TYPE
	SYNTAX      Integer32
	MAX-ACCESS  read-only
	STATUS      current
	DESCRIPTION
		""
        ::= { amp2Disp-Currents-Dividers 7 }

amp2DispCurs-Div-Current-Divider-8 OBJECT-TYPE
	SYNTAX      Integer32
	MAX-ACCESS  read-only
	STATUS      current
	DESCRIPTION
		""
        ::= { amp2Disp-Currents-Dividers 8 }

amp2DispCurs-Div-Current-Divider-9 OBJECT-TYPE
	SYNTAX      Integer32
	MAX-ACCESS  read-only
	STATUS      current
	DESCRIPTION
		""
        ::= { amp2Disp-Currents-Dividers 9 }

amp2DispCurs-Div-Current-Divider-10 OBJECT-TYPE
	SYNTAX      Integer32
	MAX-ACCESS  read-only
	STATUS      current
	DESCRIPTION
		""
        ::= { amp2Disp-Currents-Dividers 10 }

amp2DispCurs-Div-Current-Divider-11 OBJECT-TYPE
	SYNTAX      Integer32
	MAX-ACCESS  read-only
	STATUS      current
	DESCRIPTION
		""
        ::= { amp2Disp-Currents-Dividers 11 }

amp2DispCurs-Div-Current-Divider-12 OBJECT-TYPE
	SYNTAX      Integer32
	MAX-ACCESS  read-only
	STATUS      current
	DESCRIPTION
		""
        ::= { amp2Disp-Currents-Dividers 12 }

amp2DispCurs-Div-Current-Divider-13 OBJECT-TYPE
	SYNTAX      Integer32
	MAX-ACCESS  read-only
	STATUS      current
	DESCRIPTION
		""
        ::= { amp2Disp-Currents-Dividers 13 }

amp2DispCurs-Div-Current-Divider-14 OBJECT-TYPE
	SYNTAX      Integer32
	MAX-ACCESS  read-only
	STATUS      current
	DESCRIPTION
		""
        ::= { amp2Disp-Currents-Dividers 14 }

amp2DispCurs-Div-Current-Divider-15 OBJECT-TYPE
	SYNTAX      Integer32
	MAX-ACCESS  read-only
	STATUS      current
	DESCRIPTION
		""
        ::= { amp2Disp-Currents-Dividers 15 }

amp2DispCurs-Div-Current-Divider-16 OBJECT-TYPE
	SYNTAX      Integer32
	MAX-ACCESS  read-only
	STATUS      current
	DESCRIPTION
		""
        ::= { amp2Disp-Currents-Dividers 16 }

amp2DispCurs-Div-Current-Divider-17 OBJECT-TYPE
	SYNTAX      Integer32
	MAX-ACCESS  read-only
	STATUS      current
	DESCRIPTION
		""
        ::= { amp2Disp-Currents-Dividers 17 }

amp2DispCurs-Div-Current-Divider-18 OBJECT-TYPE
	SYNTAX      Integer32
	MAX-ACCESS  read-only
	STATUS      current
	DESCRIPTION
		""
        ::= { amp2Disp-Currents-Dividers 18 }

amp2DispCurs-Div-Current-Divider-19 OBJECT-TYPE
	SYNTAX      Integer32
	MAX-ACCESS  read-only
	STATUS      current
	DESCRIPTION
		""
        ::= { amp2Disp-Currents-Dividers 19 }

amp2DispCurs-Current-1 OBJECT-TYPE
	SYNTAX      Integer32
	MAX-ACCESS  read-only
	STATUS      current
	DESCRIPTION
		""
        ::= { amp2Disp-Currents 1 }

amp2DispCurs-Current-2 OBJECT-TYPE
	SYNTAX      Integer32
	MAX-ACCESS  read-only
	STATUS      current
	DESCRIPTION
		""
        ::= { amp2Disp-Currents 2 }

amp2DispCurs-Current-3 OBJECT-TYPE
	SYNTAX      Integer32
	MAX-ACCESS  read-only
	STATUS      current
	DESCRIPTION
		""
        ::= { amp2Disp-Currents 3 }

amp2DispCurs-Current-4 OBJECT-TYPE
	SYNTAX      Integer32
	MAX-ACCESS  read-only
	STATUS      current
	DESCRIPTION
		""
        ::= { amp2Disp-Currents 4 }

amp2DispCurs-Current-5 OBJECT-TYPE
	SYNTAX      Integer32
	MAX-ACCESS  read-only
	STATUS      current
	DESCRIPTION
		""
        ::= { amp2Disp-Currents 5 }

amp2DispCurs-Current-6 OBJECT-TYPE
	SYNTAX      Integer32
	MAX-ACCESS  read-only
	STATUS      current
	DESCRIPTION
		""
        ::= { amp2Disp-Currents 6 }

amp2DispCurs-Current-7 OBJECT-TYPE
	SYNTAX      Integer32
	MAX-ACCESS  read-only
	STATUS      current
	DESCRIPTION
		""
        ::= { amp2Disp-Currents 7 }

amp2DispCurs-Current-8 OBJECT-TYPE
	SYNTAX      Integer32
	MAX-ACCESS  read-only
	STATUS      current
	DESCRIPTION
		""
        ::= { amp2Disp-Currents 8 }

amp2DispCurs-Current-9 OBJECT-TYPE
	SYNTAX      Integer32
	MAX-ACCESS  read-only
	STATUS      current
	DESCRIPTION
		""
        ::= { amp2Disp-Currents 9 }

amp2DispCurs-Current-10 OBJECT-TYPE
	SYNTAX      Integer32
	MAX-ACCESS  read-only
	STATUS      current
	DESCRIPTION
		""
        ::= { amp2Disp-Currents 10 }

amp2DispCurs-Current-11 OBJECT-TYPE
	SYNTAX      Integer32
	MAX-ACCESS  read-only
	STATUS      current
	DESCRIPTION
		""
        ::= { amp2Disp-Currents 11 }

amp2DispCurs-Current-12 OBJECT-TYPE
	SYNTAX      Integer32
	MAX-ACCESS  read-only
	STATUS      current
	DESCRIPTION
		""
        ::= { amp2Disp-Currents 12 }

amp2DispCurs-Current-13 OBJECT-TYPE
	SYNTAX      Integer32
	MAX-ACCESS  read-only
	STATUS      current
	DESCRIPTION
		""
        ::= { amp2Disp-Currents 13 }

amp2DispCurs-Current-14 OBJECT-TYPE
	SYNTAX      Integer32
	MAX-ACCESS  read-only
	STATUS      current
	DESCRIPTION
		""
        ::= { amp2Disp-Currents 14 }

amp2DispCurs-Current-15 OBJECT-TYPE
	SYNTAX      Integer32
	MAX-ACCESS  read-only
	STATUS      current
	DESCRIPTION
		""
        ::= { amp2Disp-Currents 15 }

amp2DispCurs-Current-16 OBJECT-TYPE
	SYNTAX      Integer32
	MAX-ACCESS  read-only
	STATUS      current
	DESCRIPTION
		""
        ::= { amp2Disp-Currents 16 }

amp2DispCurs-Current-17 OBJECT-TYPE
	SYNTAX      Integer32
	MAX-ACCESS  read-only
	STATUS      current
	DESCRIPTION
		""
        ::= { amp2Disp-Currents 17 }

amp2DispCurs-Current-18 OBJECT-TYPE
	SYNTAX      Integer32
	MAX-ACCESS  read-only
	STATUS      current
	DESCRIPTION
		""
        ::= { amp2Disp-Currents 18 }

amp2DispCurs-Current-19 OBJECT-TYPE
	SYNTAX      Integer32
	MAX-ACCESS  read-only
	STATUS      current
	DESCRIPTION
		""
        ::= { amp2Disp-Currents 19 }

amp2DispTemps-Temperature-1 OBJECT-TYPE
	SYNTAX      Integer32
	MAX-ACCESS  read-only
	STATUS      current
	DESCRIPTION
		""
        ::= { amp2Disp-Temperatures 1 }

amp2DispTemps-Temperature-2 OBJECT-TYPE
	SYNTAX      Integer32
	MAX-ACCESS  read-only
	STATUS      current
	DESCRIPTION
		""
        ::= { amp2Disp-Temperatures 2 }

amp2DispMain-Status-Info OBJECT-TYPE
	SYNTAX      OCTET STRING
	MAX-ACCESS  read-only
	STATUS      current
	DESCRIPTION
		"Multiline, UTF8, separator: CRLF"
        ::= { amp2Disp-Main 1 }

amp2DispMain-Status-Warning OBJECT-TYPE
	SYNTAX      OCTET STRING
	MAX-ACCESS  read-only
	STATUS      current
	DESCRIPTION
		"Multiline, UTF8, separator: CRLF"
        ::= { amp2Disp-Main 2 }

amp2DispMain-Status-Failure OBJECT-TYPE
	SYNTAX      OCTET STRING
	MAX-ACCESS  read-only
	STATUS      current
	DESCRIPTION
		"Multiline, UTF8, separator: CRLF"
        ::= { amp2Disp-Main 3 }

amp2DispMain-Power-Out OBJECT-TYPE
	SYNTAX      Integer32
	MAX-ACCESS  read-only
	STATUS      current
	DESCRIPTION
		"Pout, unit: 0.1 W / 0.1 dB"
        ::= { amp2Disp-Main 4 }

amp2DispMain-Power-Average OBJECT-TYPE
	SYNTAX      Integer32
	MAX-ACCESS  read-only
	STATUS      current
	DESCRIPTION
		" PoutAvr, unit: 0.1 dB"
        ::= { amp2Disp-Main 5 }

amp2DispMain-Power-In OBJECT-TYPE
	SYNTAX      Integer32
	MAX-ACCESS  read-only
	STATUS      current
	DESCRIPTION
		"Pin, unit: 0.1 dB (-100000 = Unused)"
        ::= { amp2Disp-Main 6 }

amp2DispMain-Power-Ref OBJECT-TYPE
	SYNTAX      Integer32
	MAX-ACCESS  read-only
	STATUS      current
	DESCRIPTION
		"Pref, unit: 1/0.1/0.01 W / 1/0.1/0.01 dB, divider from ampXAux-PowerRef-Divider"
        ::= { amp2Disp-Main 7 }

amp2DispMain-Kp     OBJECT-TYPE
	SYNTAX      Integer32
	MAX-ACCESS  read-only
	STATUS      current
	DESCRIPTION
		"Kp, unit: 0.01 % (-100000 = Unused)"
        ::= { amp2Disp-Main 8 }

amp2DispMain-Phase  OBJECT-TYPE
	SYNTAX      Integer32
	MAX-ACCESS  read-only
	STATUS      current
	DESCRIPTION
		"Phase, unit: 0.1 % (-100000 = Unused)"
        ::= { amp2Disp-Main 9 }

amp2DispMain-dKp    OBJECT-TYPE
	SYNTAX      Integer32
	MAX-ACCESS  read-only
	STATUS      current
	DESCRIPTION
		"dKp, unit: 0.01 % (-100000 = Disabled)"
        ::= { amp2Disp-Main 10 }

amp2DispMain-Power-Out-2 OBJECT-TYPE
	SYNTAX      Integer32
	MAX-ACCESS  read-only
	STATUS      current
	DESCRIPTION
		"Pout2, unit: 1 W (-1 = Unused)"
        ::= { amp2Disp-Main 11 }

amp2DispMain-Profile OBJECT-TYPE
	SYNTAX      INTEGER {m1 (0), m2 (1)}
	MAX-ACCESS  read-only
	STATUS      current
	DESCRIPTION
		""
        ::= { amp2Disp-Main 12 }

amp2Aux-Status      OBJECT-TYPE
	SYNTAX      INTEGER {noFailure (0), powerOut (1), powerRef (2), powerIn (3), temperature1 (4), temperature2 (5), i1 (6), i2 (7), i3 (8), i4 (9), i5 (10), i6 (11), i7 (12), i8 (13), i9 (14), i10 (15), i11 (16), i12 (17), i13 (18), i14 (19), i15 (20), i16 (21), i17 (22), i18 (23), i19 (24), powerOutAvg (25), interErr (26), misc (31)}
	MAX-ACCESS  read-only
	STATUS      current
	DESCRIPTION
		"Amplifier internal failure status"
        ::= { amp2-Auxiliary 1 }

amp2Aux-Power-Units OBJECT-TYPE
	SYNTAX      INTEGER {none (0), watt (1), dB (2)}
	MAX-ACCESS  read-only
	STATUS      current
	DESCRIPTION
		"Amplifier Pout/Pref units: 1-W, 2-dB"
        ::= { amp2-Auxiliary 2 }

amp2Aux-Temperatures-Count OBJECT-TYPE
	SYNTAX      Integer32
	MAX-ACCESS  read-only
	STATUS      current
	DESCRIPTION
		"Temperatures sensors total count"
        ::= { amp2-Auxiliary 3 }

amp2Aux-Currents-Count OBJECT-TYPE
	SYNTAX      Integer32
	MAX-ACCESS  read-only
	STATUS      current
	DESCRIPTION
		"Currents sensors total count"
        ::= { amp2-Auxiliary 4 }

amp2Aux-Show-PowerOut-Only OBJECT-TYPE
	SYNTAX      INTEGER {false(0), true(1)}
	MAX-ACCESS  read-only
	STATUS      current
	DESCRIPTION
		"Display Pout only for main props: 0-No, 1-Yes"
        ::= { amp2-Auxiliary 5 }

amp2Aux-Show-PowerOut-Average OBJECT-TYPE
	SYNTAX      INTEGER {false(0), true(1)}
	MAX-ACCESS  read-only
	STATUS      current
	DESCRIPTION
		"Display Poutavg: 0-No, 1-Yes"
        ::= { amp2-Auxiliary 6 }

amp2Aux-Currents-Units OBJECT-TYPE
	SYNTAX      INTEGER {none (0), amper (1), percent (2)}
	MAX-ACCESS  read-only
	STATUS      current
	DESCRIPTION
		"Amplifier currents units: 1-Amperes (A), 2-Percent (%)"
        ::= { amp2-Auxiliary 7 }

amp2Aux-Show-dKp    OBJECT-TYPE
	SYNTAX      INTEGER {false(0), true(1)}
	MAX-ACCESS  read-only
	STATUS      current
	DESCRIPTION
		"Display dKp: 0-No, 1-Yes"
        ::= { amp2-Auxiliary 8 }

amp2Aux-PowerRef-Divider OBJECT-TYPE
	SYNTAX      Integer32
	MAX-ACCESS  read-only
	STATUS      current
	DESCRIPTION
		"Amplifier Pref divider: 1, 10, 100"
        ::= { amp2-Auxiliary 9 }

amp2Aux-Features    OBJECT-TYPE
	SYNTAX      Integer32
	MAX-ACCESS  read-only
	STATUS      current
	DESCRIPTION
		"Amplifier features/supports"
        ::= { amp2-Auxiliary 10 }

amp2Aux-Temperatures-Mapping OBJECT-TYPE
	SYNTAX      INTEGER {t1_T2 (0), tmax_Tps (1)}
	MAX-ACCESS  read-only
	STATUS      current
	DESCRIPTION
		"Temperatures titles mapping"
        ::= { amp2-Auxiliary 11 }

amp2Unit-Connected  OBJECT-TYPE
	SYNTAX      INTEGER {false(0), true(1)}
	MAX-ACCESS  read-only
	STATUS      current
	DESCRIPTION
		""
        ::= { amp2-Unit 1 }

amp2Unit-Warning    OBJECT-TYPE
	SYNTAX      INTEGER {false(0), true(1)}
	MAX-ACCESS  read-only
	STATUS      current
	DESCRIPTION
		""
        ::= { amp2-Unit 2 }

amp2Unit-Failure    OBJECT-TYPE
	SYNTAX      INTEGER {false(0), true(1)}
	MAX-ACCESS  read-only
	STATUS      current
	DESCRIPTION
		""
        ::= { amp2-Unit 3 }

amp2Unit-Busy       OBJECT-TYPE
	SYNTAX      Integer32
	MAX-ACCESS  read-only
	STATUS      current
	DESCRIPTION
		""
        ::= { amp2-Unit 4 }

amp2Unit-Model      OBJECT-TYPE
	SYNTAX      OCTET STRING
	MAX-ACCESS  read-only
	STATUS      current
	DESCRIPTION
		""
        ::= { amp2-Unit 5 }

amp2Unit-Serial-Number OBJECT-TYPE
	SYNTAX      Integer32
	MAX-ACCESS  read-only
	STATUS      current
	DESCRIPTION
		""
        ::= { amp2-Unit 6 }

amp2Unit-Firmware-Version OBJECT-TYPE
	SYNTAX      OCTET STRING
	MAX-ACCESS  read-only
	STATUS      current
	DESCRIPTION
		""
        ::= { amp2-Unit 7 }

amp2Unit-Uptime     OBJECT-TYPE
	SYNTAX      DateAndTime
	MAX-ACCESS  read-only
	STATUS      current
	DESCRIPTION
		""
        ::= { amp2-Unit 8 }

amp2Unit-Post-Writes-Count OBJECT-TYPE
	SYNTAX      Integer32
	MAX-ACCESS  read-only
	STATUS      current
	DESCRIPTION
		""
        ::= { amp2-Unit 9 }

amp2Unit-IP-Address OBJECT-TYPE
	SYNTAX      IPAddress
	MAX-ACCESS  read-only
	STATUS      current
	DESCRIPTION
		""
        ::= { amp2-Unit 10 }

amp2Unit-TCP-Port   OBJECT-TYPE
	SYNTAX      Integer32
	MAX-ACCESS  read-only
	STATUS      current
	DESCRIPTION
		""
        ::= { amp2-Unit 11 }

amp2Unit-Adapter    OBJECT-TYPE
	SYNTAX      OCTET STRING
	MAX-ACCESS  read-only
	STATUS      current
	DESCRIPTION
		""
        ::= { amp2-Unit 12 }

amp2Unit-Reconnects OBJECT-TYPE
	SYNTAX      Integer32
	MAX-ACCESS  read-only
	STATUS      current
	DESCRIPTION
		""
        ::= { amp2-Unit 13 }

amp1DispCurs-Div-Current-Divider-1 OBJECT-TYPE
	SYNTAX      Integer32
	MAX-ACCESS  read-only
	STATUS      current
	DESCRIPTION
		""
        ::= { amp1Disp-Currents-Dividers 1 }

amp1DispCurs-Div-Current-Divider-2 OBJECT-TYPE
	SYNTAX      Integer32
	MAX-ACCESS  read-only
	STATUS      current
	DESCRIPTION
		""
        ::= { amp1Disp-Currents-Dividers 2 }

amp1DispCurs-Div-Current-Divider-3 OBJECT-TYPE
	SYNTAX      Integer32
	MAX-ACCESS  read-only
	STATUS      current
	DESCRIPTION
		""
        ::= { amp1Disp-Currents-Dividers 3 }

amp1DispCurs-Div-Current-Divider-4 OBJECT-TYPE
	SYNTAX      Integer32
	MAX-ACCESS  read-only
	STATUS      current
	DESCRIPTION
		""
        ::= { amp1Disp-Currents-Dividers 4 }

amp1DispCurs-Div-Current-Divider-5 OBJECT-TYPE
	SYNTAX      Integer32
	MAX-ACCESS  read-only
	STATUS      current
	DESCRIPTION
		""
        ::= { amp1Disp-Currents-Dividers 5 }

amp1DispCurs-Div-Current-Divider-6 OBJECT-TYPE
	SYNTAX      Integer32
	MAX-ACCESS  read-only
	STATUS      current
	DESCRIPTION
		""
        ::= { amp1Disp-Currents-Dividers 6 }

amp1DispCurs-Div-Current-Divider-7 OBJECT-TYPE
	SYNTAX      Integer32
	MAX-ACCESS  read-only
	STATUS      current
	DESCRIPTION
		""
        ::= { amp1Disp-Currents-Dividers 7 }

amp1DispCurs-Div-Current-Divider-8 OBJECT-TYPE
	SYNTAX      Integer32
	MAX-ACCESS  read-only
	STATUS      current
	DESCRIPTION
		""
        ::= { amp1Disp-Currents-Dividers 8 }

amp1DispCurs-Div-Current-Divider-9 OBJECT-TYPE
	SYNTAX      Integer32
	MAX-ACCESS  read-only
	STATUS      current
	DESCRIPTION
		""
        ::= { amp1Disp-Currents-Dividers 9 }

amp1DispCurs-Div-Current-Divider-10 OBJECT-TYPE
	SYNTAX      Integer32
	MAX-ACCESS  read-only
	STATUS      current
	DESCRIPTION
		""
        ::= { amp1Disp-Currents-Dividers 10 }

amp1DispCurs-Div-Current-Divider-11 OBJECT-TYPE
	SYNTAX      Integer32
	MAX-ACCESS  read-only
	STATUS      current
	DESCRIPTION
		""
        ::= { amp1Disp-Currents-Dividers 11 }

amp1DispCurs-Div-Current-Divider-12 OBJECT-TYPE
	SYNTAX      Integer32
	MAX-ACCESS  read-only
	STATUS      current
	DESCRIPTION
		""
        ::= { amp1Disp-Currents-Dividers 12 }

amp1DispCurs-Div-Current-Divider-13 OBJECT-TYPE
	SYNTAX      Integer32
	MAX-ACCESS  read-only
	STATUS      current
	DESCRIPTION
		""
        ::= { amp1Disp-Currents-Dividers 13 }

amp1DispCurs-Div-Current-Divider-14 OBJECT-TYPE
	SYNTAX      Integer32
	MAX-ACCESS  read-only
	STATUS      current
	DESCRIPTION
		""
        ::= { amp1Disp-Currents-Dividers 14 }

amp1DispCurs-Div-Current-Divider-15 OBJECT-TYPE
	SYNTAX      Integer32
	MAX-ACCESS  read-only
	STATUS      current
	DESCRIPTION
		""
        ::= { amp1Disp-Currents-Dividers 15 }

amp1DispCurs-Div-Current-Divider-16 OBJECT-TYPE
	SYNTAX      Integer32
	MAX-ACCESS  read-only
	STATUS      current
	DESCRIPTION
		""
        ::= { amp1Disp-Currents-Dividers 16 }

amp1DispCurs-Div-Current-Divider-17 OBJECT-TYPE
	SYNTAX      Integer32
	MAX-ACCESS  read-only
	STATUS      current
	DESCRIPTION
		""
        ::= { amp1Disp-Currents-Dividers 17 }

amp1DispCurs-Div-Current-Divider-18 OBJECT-TYPE
	SYNTAX      Integer32
	MAX-ACCESS  read-only
	STATUS      current
	DESCRIPTION
		""
        ::= { amp1Disp-Currents-Dividers 18 }

amp1DispCurs-Div-Current-Divider-19 OBJECT-TYPE
	SYNTAX      Integer32
	MAX-ACCESS  read-only
	STATUS      current
	DESCRIPTION
		""
        ::= { amp1Disp-Currents-Dividers 19 }

amp1DispCurs-Current-1 OBJECT-TYPE
	SYNTAX      Integer32
	MAX-ACCESS  read-only
	STATUS      current
	DESCRIPTION
		""
        ::= { amp1Disp-Currents 1 }

amp1DispCurs-Current-2 OBJECT-TYPE
	SYNTAX      Integer32
	MAX-ACCESS  read-only
	STATUS      current
	DESCRIPTION
		""
        ::= { amp1Disp-Currents 2 }

amp1DispCurs-Current-3 OBJECT-TYPE
	SYNTAX      Integer32
	MAX-ACCESS  read-only
	STATUS      current
	DESCRIPTION
		""
        ::= { amp1Disp-Currents 3 }

amp1DispCurs-Current-4 OBJECT-TYPE
	SYNTAX      Integer32
	MAX-ACCESS  read-only
	STATUS      current
	DESCRIPTION
		""
        ::= { amp1Disp-Currents 4 }

amp1DispCurs-Current-5 OBJECT-TYPE
	SYNTAX      Integer32
	MAX-ACCESS  read-only
	STATUS      current
	DESCRIPTION
		""
        ::= { amp1Disp-Currents 5 }

amp1DispCurs-Current-6 OBJECT-TYPE
	SYNTAX      Integer32
	MAX-ACCESS  read-only
	STATUS      current
	DESCRIPTION
		""
        ::= { amp1Disp-Currents 6 }

amp1DispCurs-Current-7 OBJECT-TYPE
	SYNTAX      Integer32
	MAX-ACCESS  read-only
	STATUS      current
	DESCRIPTION
		""
        ::= { amp1Disp-Currents 7 }

amp1DispCurs-Current-8 OBJECT-TYPE
	SYNTAX      Integer32
	MAX-ACCESS  read-only
	STATUS      current
	DESCRIPTION
		""
        ::= { amp1Disp-Currents 8 }

amp1DispCurs-Current-9 OBJECT-TYPE
	SYNTAX      Integer32
	MAX-ACCESS  read-only
	STATUS      current
	DESCRIPTION
		""
        ::= { amp1Disp-Currents 9 }

amp1DispCurs-Current-10 OBJECT-TYPE
	SYNTAX      Integer32
	MAX-ACCESS  read-only
	STATUS      current
	DESCRIPTION
		""
        ::= { amp1Disp-Currents 10 }

amp1DispCurs-Current-11 OBJECT-TYPE
	SYNTAX      Integer32
	MAX-ACCESS  read-only
	STATUS      current
	DESCRIPTION
		""
        ::= { amp1Disp-Currents 11 }

amp1DispCurs-Current-12 OBJECT-TYPE
	SYNTAX      Integer32
	MAX-ACCESS  read-only
	STATUS      current
	DESCRIPTION
		""
        ::= { amp1Disp-Currents 12 }

amp1DispCurs-Current-13 OBJECT-TYPE
	SYNTAX      Integer32
	MAX-ACCESS  read-only
	STATUS      current
	DESCRIPTION
		""
        ::= { amp1Disp-Currents 13 }

amp1DispCurs-Current-14 OBJECT-TYPE
	SYNTAX      Integer32
	MAX-ACCESS  read-only
	STATUS      current
	DESCRIPTION
		""
        ::= { amp1Disp-Currents 14 }

amp1DispCurs-Current-15 OBJECT-TYPE
	SYNTAX      Integer32
	MAX-ACCESS  read-only
	STATUS      current
	DESCRIPTION
		""
        ::= { amp1Disp-Currents 15 }

amp1DispCurs-Current-16 OBJECT-TYPE
	SYNTAX      Integer32
	MAX-ACCESS  read-only
	STATUS      current
	DESCRIPTION
		""
        ::= { amp1Disp-Currents 16 }

amp1DispCurs-Current-17 OBJECT-TYPE
	SYNTAX      Integer32
	MAX-ACCESS  read-only
	STATUS      current
	DESCRIPTION
		""
        ::= { amp1Disp-Currents 17 }

amp1DispCurs-Current-18 OBJECT-TYPE
	SYNTAX      Integer32
	MAX-ACCESS  read-only
	STATUS      current
	DESCRIPTION
		""
        ::= { amp1Disp-Currents 18 }

amp1DispCurs-Current-19 OBJECT-TYPE
	SYNTAX      Integer32
	MAX-ACCESS  read-only
	STATUS      current
	DESCRIPTION
		""
        ::= { amp1Disp-Currents 19 }

amp1DispTemps-Temperature-1 OBJECT-TYPE
	SYNTAX      Integer32
	MAX-ACCESS  read-only
	STATUS      current
	DESCRIPTION
		""
        ::= { amp1Disp-Temperatures 1 }

amp1DispTemps-Temperature-2 OBJECT-TYPE
	SYNTAX      Integer32
	MAX-ACCESS  read-only
	STATUS      current
	DESCRIPTION
		""
        ::= { amp1Disp-Temperatures 2 }

amp1DispMain-Status-Info OBJECT-TYPE
	SYNTAX      OCTET STRING
	MAX-ACCESS  read-only
	STATUS      current
	DESCRIPTION
		"Multiline, UTF8, separator: CRLF"
        ::= { amp1Disp-Main 1 }

amp1DispMain-Status-Warning OBJECT-TYPE
	SYNTAX      OCTET STRING
	MAX-ACCESS  read-only
	STATUS      current
	DESCRIPTION
		"Multiline, UTF8, separator: CRLF"
        ::= { amp1Disp-Main 2 }

amp1DispMain-Status-Failure OBJECT-TYPE
	SYNTAX      OCTET STRING
	MAX-ACCESS  read-only
	STATUS      current
	DESCRIPTION
		"Multiline, UTF8, separator: CRLF"
        ::= { amp1Disp-Main 3 }

amp1DispMain-Power-Out OBJECT-TYPE
	SYNTAX      Integer32
	MAX-ACCESS  read-only
	STATUS      current
	DESCRIPTION
		"Pout, unit: 0.1 W / 0.1 dB"
        ::= { amp1Disp-Main 4 }

amp1DispMain-Power-Average OBJECT-TYPE
	SYNTAX      Integer32
	MAX-ACCESS  read-only
	STATUS      current
	DESCRIPTION
		" PoutAvr, unit: 0.1 dB"
        ::= { amp1Disp-Main 5 }

amp1DispMain-Power-In OBJECT-TYPE
	SYNTAX      Integer32
	MAX-ACCESS  read-only
	STATUS      current
	DESCRIPTION
		"Pin, unit: 0.1 dB (-100000 = Unused)"
        ::= { amp1Disp-Main 6 }

amp1DispMain-Power-Ref OBJECT-TYPE
	SYNTAX      Integer32
	MAX-ACCESS  read-only
	STATUS      current
	DESCRIPTION
		"Pref, unit: 1/0.1/0.01 W / 1/0.1/0.01 dB, divider from ampXAux-PowerRef-Divider"
        ::= { amp1Disp-Main 7 }

amp1DispMain-Kp     OBJECT-TYPE
	SYNTAX      Integer32
	MAX-ACCESS  read-only
	STATUS      current
	DESCRIPTION
		"Kp, unit: 0.01 % (-100000 = Unused)"
        ::= { amp1Disp-Main 8 }

amp1DispMain-Phase  OBJECT-TYPE
	SYNTAX      Integer32
	MAX-ACCESS  read-only
	STATUS      current
	DESCRIPTION
		"Phase, unit: 0.1 % (-100000 = Unused)"
        ::= { amp1Disp-Main 9 }

amp1DispMain-dKp    OBJECT-TYPE
	SYNTAX      Integer32
	MAX-ACCESS  read-only
	STATUS      current
	DESCRIPTION
		"dKp, unit: 0.01 % (-100000 = Disabled)"
        ::= { amp1Disp-Main 10 }

amp1DispMain-Power-Out-2 OBJECT-TYPE
	SYNTAX      Integer32
	MAX-ACCESS  read-only
	STATUS      current
	DESCRIPTION
		"Pout2, unit: 1 W (-1 = Unused)"
        ::= { amp1Disp-Main 11 }

amp1DispMain-Profile OBJECT-TYPE
	SYNTAX      INTEGER {m1 (0), m2 (1)}
	MAX-ACCESS  read-only
	STATUS      current
	DESCRIPTION
		""
        ::= { amp1Disp-Main 12 }

amp1Aux-Status      OBJECT-TYPE
	SYNTAX      INTEGER {noFailure (0), powerOut (1), powerRef (2), powerIn (3), temperature1 (4), temperature2 (5), i1 (6), i2 (7), i3 (8), i4 (9), i5 (10), i6 (11), i7 (12), i8 (13), i9 (14), i10 (15), i11 (16), i12 (17), i13 (18), i14 (19), i15 (20), i16 (21), i17 (22), i18 (23), i19 (24), powerOutAvg (25), interErr (26), misc (31)}
	MAX-ACCESS  read-only
	STATUS      current
	DESCRIPTION
		"Amplifier internal failure status"
        ::= { amp1-Auxiliary 1 }

amp1Aux-Power-Units OBJECT-TYPE
	SYNTAX      INTEGER {none (0), watt (1), dB (2)}
	MAX-ACCESS  read-only
	STATUS      current
	DESCRIPTION
		"Amplifier Pout/Pref units: 1-W, 2-dB"
        ::= { amp1-Auxiliary 2 }

amp1Aux-Temperatures-Count OBJECT-TYPE
	SYNTAX      Integer32
	MAX-ACCESS  read-only
	STATUS      current
	DESCRIPTION
		"Temperatures sensors total count"
        ::= { amp1-Auxiliary 3 }

amp1Aux-Currents-Count OBJECT-TYPE
	SYNTAX      Integer32
	MAX-ACCESS  read-only
	STATUS      current
	DESCRIPTION
		"Currents sensors total count"
        ::= { amp1-Auxiliary 4 }

amp1Aux-Show-PowerOut-Only OBJECT-TYPE
	SYNTAX      INTEGER {false(0), true(1)}
	MAX-ACCESS  read-only
	STATUS      current
	DESCRIPTION
		"Display Pout only for main props: 0-No, 1-Yes"
        ::= { amp1-Auxiliary 5 }

amp1Aux-Show-PowerOut-Average OBJECT-TYPE
	SYNTAX      INTEGER {false(0), true(1)}
	MAX-ACCESS  read-only
	STATUS      current
	DESCRIPTION
		"Display Poutavg: 0-No, 1-Yes"
        ::= { amp1-Auxiliary 6 }

amp1Aux-Currents-Units OBJECT-TYPE
	SYNTAX      INTEGER {none (0), amper (1), percent (2)}
	MAX-ACCESS  read-only
	STATUS      current
	DESCRIPTION
		"Amplifier currents units: 1-Amperes (A), 2-Percent (%)"
        ::= { amp1-Auxiliary 7 }

amp1Aux-Show-dKp    OBJECT-TYPE
	SYNTAX      INTEGER {false(0), true(1)}
	MAX-ACCESS  read-only
	STATUS      current
	DESCRIPTION
		"Display dKp: 0-No, 1-Yes"
        ::= { amp1-Auxiliary 8 }

amp1Aux-PowerRef-Divider OBJECT-TYPE
	SYNTAX      Integer32
	MAX-ACCESS  read-only
	STATUS      current
	DESCRIPTION
		"Amplifier Pref divider: 1, 10, 100"
        ::= { amp1-Auxiliary 9 }

amp1Aux-Features    OBJECT-TYPE
	SYNTAX      Integer32
	MAX-ACCESS  read-only
	STATUS      current
	DESCRIPTION
		"Amplifier features/supports"
        ::= { amp1-Auxiliary 10 }

amp1Aux-Temperatures-Mapping OBJECT-TYPE
	SYNTAX      INTEGER {t1_T2 (0), tmax_Tps (1)}
	MAX-ACCESS  read-only
	STATUS      current
	DESCRIPTION
		"Temperatures titles mapping"
        ::= { amp1-Auxiliary 11 }

amp1Unit-Connected  OBJECT-TYPE
	SYNTAX      INTEGER {false(0), true(1)}
	MAX-ACCESS  read-only
	STATUS      current
	DESCRIPTION
		""
        ::= { amp1-Unit 1 }

amp1Unit-Warning    OBJECT-TYPE
	SYNTAX      INTEGER {false(0), true(1)}
	MAX-ACCESS  read-only
	STATUS      current
	DESCRIPTION
		""
        ::= { amp1-Unit 2 }

amp1Unit-Failure    OBJECT-TYPE
	SYNTAX      INTEGER {false(0), true(1)}
	MAX-ACCESS  read-only
	STATUS      current
	DESCRIPTION
		""
        ::= { amp1-Unit 3 }

amp1Unit-Busy       OBJECT-TYPE
	SYNTAX      Integer32
	MAX-ACCESS  read-only
	STATUS      current
	DESCRIPTION
		""
        ::= { amp1-Unit 4 }

amp1Unit-Model      OBJECT-TYPE
	SYNTAX      OCTET STRING
	MAX-ACCESS  read-only
	STATUS      current
	DESCRIPTION
		""
        ::= { amp1-Unit 5 }

amp1Unit-Serial-Number OBJECT-TYPE
	SYNTAX      Integer32
	MAX-ACCESS  read-only
	STATUS      current
	DESCRIPTION
		""
        ::= { amp1-Unit 6 }

amp1Unit-Firmware-Version OBJECT-TYPE
	SYNTAX      OCTET STRING
	MAX-ACCESS  read-only
	STATUS      current
	DESCRIPTION
		""
        ::= { amp1-Unit 7 }

amp1Unit-Uptime     OBJECT-TYPE
	SYNTAX      DateAndTime
	MAX-ACCESS  read-only
	STATUS      current
	DESCRIPTION
		""
        ::= { amp1-Unit 8 }

amp1Unit-Post-Writes-Count OBJECT-TYPE
	SYNTAX      Integer32
	MAX-ACCESS  read-only
	STATUS      current
	DESCRIPTION
		""
        ::= { amp1-Unit 9 }

amp1Unit-IP-Address OBJECT-TYPE
	SYNTAX      IPAddress
	MAX-ACCESS  read-only
	STATUS      current
	DESCRIPTION
		""
        ::= { amp1-Unit 10 }

amp1Unit-TCP-Port   OBJECT-TYPE
	SYNTAX      Integer32
	MAX-ACCESS  read-only
	STATUS      current
	DESCRIPTION
		""
        ::= { amp1-Unit 11 }

amp1Unit-Adapter    OBJECT-TYPE
	SYNTAX      OCTET STRING
	MAX-ACCESS  read-only
	STATUS      current
	DESCRIPTION
		""
        ::= { amp1-Unit 12 }

amp1Unit-Reconnects OBJECT-TYPE
	SYNTAX      Integer32
	MAX-ACCESS  read-only
	STATUS      current
	DESCRIPTION
		""
        ::= { amp1-Unit 13 }

exc2-Unified-Is-Busy OBJECT-TYPE
	SYNTAX      INTEGER {false(0), true(1)}
	MAX-ACCESS  read-only
	STATUS      current
	DESCRIPTION
		""
        ::= { exc2-Unified 1 }

exc2-Unified-Is-Mute OBJECT-TYPE
	SYNTAX      INTEGER {false(0), true(1)}
	MAX-ACCESS  read-write
	STATUS      current
	DESCRIPTION
		""
        ::= { exc2-Unified 2 }

exc2-Messages-Settings-Errors OBJECT-TYPE
	SYNTAX      OCTET STRING
	MAX-ACCESS  read-only
	STATUS      current
	DESCRIPTION
		""
        ::= { exc2-Messages 1 }

exc2-Messages-Failures OBJECT-TYPE
	SYNTAX      OCTET STRING
	MAX-ACCESS  read-only
	STATUS      current
	DESCRIPTION
		""
        ::= { exc2-Messages 2 }

exc2-Messages-Warnings OBJECT-TYPE
	SYNTAX      OCTET STRING
	MAX-ACCESS  read-only
	STATUS      current
	DESCRIPTION
		""
        ::= { exc2-Messages 3 }

exc2-Messages-Information OBJECT-TYPE
	SYNTAX      OCTET STRING
	MAX-ACCESS  read-only
	STATUS      current
	DESCRIPTION
		""
        ::= { exc2-Messages 4 }

exc2-Param-Precorrection-Lin-Ctl-Enabled OBJECT-TYPE
	SYNTAX      INTEGER {false(0), true(1)}
	MAX-ACCESS  read-write
	STATUS      current
	DESCRIPTION
		""
        ::= { exc2-Param-Precorrection-Lin-Control 1 }

exc2-Param-Precorrection-Lin-Ctl-Adaptation-Process OBJECT-TYPE
	SYNTAX      INTEGER {disabled (0), dAP (1)}
	MAX-ACCESS  read-write
	STATUS      current
	DESCRIPTION
		""
        ::= { exc2-Param-Precorrection-Lin-Control 2 }

exc2-Param-Precorrection-Lin-Ctl-Adaptation-Timeout OBJECT-TYPE
	SYNTAX      Integer32
	MAX-ACCESS  read-write
	STATUS      current
	DESCRIPTION
		""
        ::= { exc2-Param-Precorrection-Lin-Control 3 }

exc2-Param-Precorrection-Lin-Ctl-Reset OBJECT-TYPE
	SYNTAX      Integer32
	MAX-ACCESS  read-write
	STATUS      current
	DESCRIPTION
		"Set value 1 to reset Linear precorrection. Other values are ignored."
        ::= { exc2-Param-Precorrection-Lin-Control 4 }

exc2-Param-Precorrection-Lin-Ctl-Start OBJECT-TYPE
	SYNTAX      Integer32
	MAX-ACCESS  read-write
	STATUS      current
	DESCRIPTION
		"Set value 1 to start Linear precorrection. Other values are ignored."
        ::= { exc2-Param-Precorrection-Lin-Control 5 }

exc2-Param-Precorrection-Lin-Ctl-Stop OBJECT-TYPE
	SYNTAX      Integer32
	MAX-ACCESS  read-write
	STATUS      current
	DESCRIPTION
		"Set value 1 to stop Linear precorrection. Other values are ignored."
        ::= { exc2-Param-Precorrection-Lin-Control 6 }

exc2-Param-Precorrection-Lin-Mon-Algorithm-Status OBJECT-TYPE
	SYNTAX      INTEGER {noStatus (0), active (1), stoppedByUser (2), stoppedByTimeout (4), stoppedByUnstable (8)}
	MAX-ACCESS  read-only
	STATUS      current
	DESCRIPTION
		""
        ::= { exc2-Param-Precorrection-Lin-Monitoring 1 }

exc2-Param-Precorrection-Lin-Mon-Is-AGC-Lock OBJECT-TYPE
	SYNTAX      INTEGER {false(0), true(1)}
	MAX-ACCESS  read-only
	STATUS      current
	DESCRIPTION
		""
        ::= { exc2-Param-Precorrection-Lin-Monitoring 2 }

exc2-Param-Precorrection-Lin-Mon-Is-Synchronization OBJECT-TYPE
	SYNTAX      INTEGER {false(0), true(1)}
	MAX-ACCESS  read-only
	STATUS      current
	DESCRIPTION
		""
        ::= { exc2-Param-Precorrection-Lin-Monitoring 3 }

exc2-Param-Precorrection-Lin-Mon-Is-Input-Power-Low OBJECT-TYPE
	SYNTAX      INTEGER {false(0), true(1)}
	MAX-ACCESS  read-only
	STATUS      current
	DESCRIPTION
		""
        ::= { exc2-Param-Precorrection-Lin-Monitoring 4 }

exc2-Param-Precorrection-Lin-Mon-Is-Input-Power-High OBJECT-TYPE
	SYNTAX      INTEGER {false(0), true(1)}
	MAX-ACCESS  read-only
	STATUS      current
	DESCRIPTION
		""
        ::= { exc2-Param-Precorrection-Lin-Monitoring 5 }

exc2-Param-Precorrection-Lin-Mon-Input-Level OBJECT-TYPE
	SYNTAX      Integer32
	MAX-ACCESS  read-only
	STATUS      current
	DESCRIPTION
		""
        ::= { exc2-Param-Precorrection-Lin-Monitoring 6 }

exc2-Param-Precorrection-Lin-Mon-Ripple-Value OBJECT-TYPE
	SYNTAX      Integer32
	MAX-ACCESS  read-only
	STATUS      current
	DESCRIPTION
		""
        ::= { exc2-Param-Precorrection-Lin-Monitoring 7 }

exc2-Param-Precorrection-Lin-Mon-Elapsed-Time-After-DAP OBJECT-TYPE
	SYNTAX      Integer32
	MAX-ACCESS  read-only
	STATUS      current
	DESCRIPTION
		""
        ::= { exc2-Param-Precorrection-Lin-Monitoring 8 }

exc2-Param-Precorrection-NonLin-Ctl-Enabled OBJECT-TYPE
	SYNTAX      INTEGER {false(0), true(1)}
	MAX-ACCESS  read-write
	STATUS      current
	DESCRIPTION
		""
        ::= { exc2-Param-Precorrection-NonLin-Control 1 }

exc2-Param-Precorrection-NonLin-Ctl-Adaptation-Process OBJECT-TYPE
	SYNTAX      INTEGER {disabled (0), singleMode (1), nA (2), continuousMode (3)}
	MAX-ACCESS  read-write
	STATUS      current
	DESCRIPTION
		""
        ::= { exc2-Param-Precorrection-NonLin-Control 2 }

exc2-Param-Precorrection-NonLin-Ctl-Adaptation-Timeout OBJECT-TYPE
	SYNTAX      Integer32
	MAX-ACCESS  read-write
	STATUS      current
	DESCRIPTION
		""
        ::= { exc2-Param-Precorrection-NonLin-Control 3 }

exc2-Param-Precorrection-NonLin-Ctl-DAP-Mode OBJECT-TYPE
	SYNTAX      INTEGER {standard_Basic (0), advanced_GAP (1)}
	MAX-ACCESS  read-write
	STATUS      current
	DESCRIPTION
		""
        ::= { exc2-Param-Precorrection-NonLin-Control 4 }

exc2-Param-Precorrection-NonLin-Ctl-Reset OBJECT-TYPE
	SYNTAX      Integer32
	MAX-ACCESS  read-write
	STATUS      current
	DESCRIPTION
		"Set value 1 to reset Non-Linear precorrection. Other values are ignored."
        ::= { exc2-Param-Precorrection-NonLin-Control 5 }

exc2-Param-Precorrection-NonLin-Ctl-Start OBJECT-TYPE
	SYNTAX      Integer32
	MAX-ACCESS  read-write
	STATUS      current
	DESCRIPTION
		"Set value 1 to start Non-Linear precorrection. Other values are ignored."
        ::= { exc2-Param-Precorrection-NonLin-Control 6 }

exc2-Param-Precorrection-NonLin-Ctl-Stop OBJECT-TYPE
	SYNTAX      Integer32
	MAX-ACCESS  read-write
	STATUS      current
	DESCRIPTION
		"Set value 1 to stop Non-Linear precorrection. Other values are ignored."
        ::= { exc2-Param-Precorrection-NonLin-Control 7 }

exc2-Param-Precorrection-NonLin-Mon-Algorithm-Status OBJECT-TYPE
	SYNTAX      INTEGER {noStatus (0), active (1), stoppedByUser (2), stoppedByTimeout (4), nA (8), stoppedByUnstable (16)}
	MAX-ACCESS  read-only
	STATUS      current
	DESCRIPTION
		""
        ::= { exc2-Param-Precorrection-NonLin-Monitoring 1 }

exc2-Param-Precorrection-NonLin-Mon-Is-AGC-Lock OBJECT-TYPE
	SYNTAX      INTEGER {false(0), true(1)}
	MAX-ACCESS  read-only
	STATUS      current
	DESCRIPTION
		""
        ::= { exc2-Param-Precorrection-NonLin-Monitoring 2 }

exc2-Param-Precorrection-NonLin-Mon-Is-Synchronization OBJECT-TYPE
	SYNTAX      INTEGER {false(0), true(1)}
	MAX-ACCESS  read-only
	STATUS      current
	DESCRIPTION
		""
        ::= { exc2-Param-Precorrection-NonLin-Monitoring 3 }

exc2-Param-Precorrection-NonLin-Mon-Is-Input-Power-Low OBJECT-TYPE
	SYNTAX      INTEGER {false(0), true(1)}
	MAX-ACCESS  read-only
	STATUS      current
	DESCRIPTION
		""
        ::= { exc2-Param-Precorrection-NonLin-Monitoring 4 }

exc2-Param-Precorrection-NonLin-Mon-Is-Input-Power-High OBJECT-TYPE
	SYNTAX      INTEGER {false(0), true(1)}
	MAX-ACCESS  read-only
	STATUS      current
	DESCRIPTION
		""
        ::= { exc2-Param-Precorrection-NonLin-Monitoring 5 }

exc2-Param-Precorrection-NonLin-Mon-Input-Level OBJECT-TYPE
	SYNTAX      Integer32
	MAX-ACCESS  read-only
	STATUS      current
	DESCRIPTION
		""
        ::= { exc2-Param-Precorrection-NonLin-Monitoring 6 }

exc2-Param-Precorrection-NonLin-Mon-Left-Shoulder OBJECT-TYPE
	SYNTAX      Integer32
	MAX-ACCESS  read-only
	STATUS      current
	DESCRIPTION
		""
        ::= { exc2-Param-Precorrection-NonLin-Monitoring 7 }

exc2-Param-Precorrection-NonLin-Mon-Right-Shoulder OBJECT-TYPE
	SYNTAX      Integer32
	MAX-ACCESS  read-only
	STATUS      current
	DESCRIPTION
		""
        ::= { exc2-Param-Precorrection-NonLin-Monitoring 8 }

exc2-Param-Precorrection-NonLin-Mon-Elapsed-Time-After-DAP OBJECT-TYPE
	SYNTAX      Integer32
	MAX-ACCESS  read-only
	STATUS      current
	DESCRIPTION
		""
        ::= { exc2-Param-Precorrection-NonLin-Monitoring 9 }

exc2-Param-Precorrection-NonLin-Mon-MER OBJECT-TYPE
	SYNTAX      Integer32
	MAX-ACCESS  read-only
	STATUS      current
	DESCRIPTION
		"-1 = N/A"
        ::= { exc2-Param-Precorrection-NonLin-Monitoring 10 }

exc2-Param-Precorrection-NonLin-Mon-Crest-Factor OBJECT-TYPE
	SYNTAX      Integer32
	MAX-ACCESS  read-only
	STATUS      current
	DESCRIPTION
		"-1 = N/A"
        ::= { exc2-Param-Precorrection-NonLin-Monitoring 11 }

exc2-Param-Firmware-Update-Progress OBJECT-TYPE
	SYNTAX      Integer32
	MAX-ACCESS  read-only
	STATUS      current
	DESCRIPTION
		""
        ::= { exc2-Param-Firmware 1 }

exc2-Param-Firmware-Switch OBJECT-TYPE
	SYNTAX      Integer32
	MAX-ACCESS  read-write
	STATUS      current
	DESCRIPTION
		"Set value 1 to activate new firmware and reboot DVB-T/T2 module. Other values are ignored."
        ::= { exc2-Param-Firmware 2 }

exc2-Param-Service-Control-Standard OBJECT-TYPE
	SYNTAX      INTEGER {dVBTH (0), dVBT2 (4)}
	MAX-ACCESS  read-write
	STATUS      current
	DESCRIPTION
		""
        ::= { exc2-Param-Service-Control 1 }

exc2-Param-Service-Control-Stream-1-Monitoring OBJECT-TYPE
	SYNTAX      INTEGER {false(0), true(1)}
	MAX-ACCESS  read-write
	STATUS      current
	DESCRIPTION
		""
        ::= { exc2-Param-Service-Control 2 }

exc2-Param-Service-Control-Stream-2-Monitoring OBJECT-TYPE
	SYNTAX      INTEGER {false(0), true(1)}
	MAX-ACCESS  read-write
	STATUS      current
	DESCRIPTION
		""
        ::= { exc2-Param-Service-Control 3 }

exc2-Param-Service-Control-Reboot-MT2 OBJECT-TYPE
	SYNTAX      Integer32
	MAX-ACCESS  read-write
	STATUS      current
	DESCRIPTION
		"Set value 1 to reboot DVB-T/T2 module. Other values are ignored."
        ::= { exc2-Param-Service-Control 4 }

exc2-Param-Service-Control-Reboot-Controller OBJECT-TYPE
	SYNTAX      Integer32
	MAX-ACCESS  read-write
	STATUS      current
	DESCRIPTION
		"Set value 2 to reboot controller. Other values are ignored."
        ::= { exc2-Param-Service-Control 5 }

exc2-Param-Service-Monitoring-DVB-T2-Support OBJECT-TYPE
	SYNTAX      INTEGER {false(0), true(1)}
	MAX-ACCESS  read-only
	STATUS      current
	DESCRIPTION
		""
        ::= { exc2-Param-Service-Monitoring 1 }

exc2-Param-Service-Monitoring-DVB-TH-Support OBJECT-TYPE
	SYNTAX      INTEGER {false(0), true(1)}
	MAX-ACCESS  read-only
	STATUS      current
	DESCRIPTION
		""
        ::= { exc2-Param-Service-Monitoring 2 }

exc2-Param-Service-Monitoring-Controller-Serial-Number OBJECT-TYPE
	SYNTAX      OCTET STRING
	MAX-ACCESS  read-only
	STATUS      current
	DESCRIPTION
		""
        ::= { exc2-Param-Service-Monitoring 3 }

exc2-Param-Service-Monitoring-Controller-Hardware-Version OBJECT-TYPE
	SYNTAX      OCTET STRING
	MAX-ACCESS  read-only
	STATUS      current
	DESCRIPTION
		""
        ::= { exc2-Param-Service-Monitoring 4 }

exc2-Param-Service-Monitoring-Controller-Software-Version OBJECT-TYPE
	SYNTAX      OCTET STRING
	MAX-ACCESS  read-only
	STATUS      current
	DESCRIPTION
		""
        ::= { exc2-Param-Service-Monitoring 5 }

exc2-Param-Service-Monitoring-MT2-Serial-Number OBJECT-TYPE
	SYNTAX      OCTET STRING
	MAX-ACCESS  read-only
	STATUS      current
	DESCRIPTION
		""
        ::= { exc2-Param-Service-Monitoring 6 }

exc2-Param-Service-Monitoring-MT2-Hardware-Version OBJECT-TYPE
	SYNTAX      OCTET STRING
	MAX-ACCESS  read-only
	STATUS      current
	DESCRIPTION
		""
        ::= { exc2-Param-Service-Monitoring 7 }

exc2-Param-Service-Monitoring-MT2-Software-Version OBJECT-TYPE
	SYNTAX      OCTET STRING
	MAX-ACCESS  read-only
	STATUS      current
	DESCRIPTION
		""
        ::= { exc2-Param-Service-Monitoring 8 }

exc2-Param-Service-Monitoring-MT2-Type OBJECT-TYPE
	SYNTAX      OCTET STRING
	MAX-ACCESS  read-only
	STATUS      current
	DESCRIPTION
		""
        ::= { exc2-Param-Service-Monitoring 9 }

exc2-Param-Tests-PRBS-23-bits OBJECT-TYPE
	SYNTAX      INTEGER {false(0), true(1)}
	MAX-ACCESS  read-write
	STATUS      current
	DESCRIPTION
		""
        ::= { exc2-Param-Tests 1 }

exc2-Param-Tests-Central-Carriers-251-Canceled OBJECT-TYPE
	SYNTAX      INTEGER {false(0), true(1)}
	MAX-ACCESS  read-write
	STATUS      current
	DESCRIPTION
		""
        ::= { exc2-Param-Tests 2 }

exc2-Param-T2-PLP-B-Number-of-PLPs OBJECT-TYPE
	SYNTAX      Integer32
	MAX-ACCESS  read-only
	STATUS      current
	DESCRIPTION
		""
        ::= { exc2-Param-T2-PLP-System-B 1 }

exc2-Param-T2-PLP-B-Column-16-PLP-ID OBJECT-TYPE
	SYNTAX      Integer32
	MAX-ACCESS  read-only
	STATUS      current
	DESCRIPTION
		""
        ::= { exc2-Param-T2-PLP-B-Column-16 1 }

exc2-Param-T2-PLP-B-Column-16-PLP-Type OBJECT-TYPE
	SYNTAX      INTEGER {common (0), type1 (1), type2 (2)}
	MAX-ACCESS  read-only
	STATUS      current
	DESCRIPTION
		""
        ::= { exc2-Param-T2-PLP-B-Column-16 2 }

exc2-Param-T2-PLP-B-Column-16-LDPC OBJECT-TYPE
	SYNTAX      INTEGER {lDPC_16K (0), lDPC_64K (1)}
	MAX-ACCESS  read-only
	STATUS      current
	DESCRIPTION
		""
        ::= { exc2-Param-T2-PLP-B-Column-16 3 }

exc2-Param-T2-PLP-B-Column-16-Coderate OBJECT-TYPE
	SYNTAX      INTEGER {rate_1_2 (0), rate_3_5 (1), rate_2_3 (2), rate_3_4 (3), rate_4_5 (4), rate_5_6 (5)}
	MAX-ACCESS  read-only
	STATUS      current
	DESCRIPTION
		""
        ::= { exc2-Param-T2-PLP-B-Column-16 4 }

exc2-Param-T2-PLP-B-Column-16-Modulation OBJECT-TYPE
	SYNTAX      INTEGER {qPSK (0), qAM_16 (1), qAM_64 (2), qAM_256 (3)}
	MAX-ACCESS  read-only
	STATUS      current
	DESCRIPTION
		""
        ::= { exc2-Param-T2-PLP-B-Column-16 5 }

exc2-Param-T2-PLP-B-Column-16-Rotated-Constellation OBJECT-TYPE
	SYNTAX      INTEGER {notUsed (0), used (1)}
	MAX-ACCESS  read-only
	STATUS      current
	DESCRIPTION
		""
        ::= { exc2-Param-T2-PLP-B-Column-16 6 }

exc2-Param-T2-PLP-B-Column-16-Time-Interleave-Type OBJECT-TYPE
	SYNTAX      INTEGER {oneT2Frame (0), severalT2Frames (1), bypassed (2)}
	MAX-ACCESS  read-only
	STATUS      current
	DESCRIPTION
		""
        ::= { exc2-Param-T2-PLP-B-Column-16 7 }

exc2-Param-T2-PLP-B-Column-16-Time-Interleave-Length OBJECT-TYPE
	SYNTAX      Integer32
	MAX-ACCESS  read-only
	STATUS      current
	DESCRIPTION
		""
        ::= { exc2-Param-T2-PLP-B-Column-16 8 }

exc2-Param-T2-PLP-B-Column-16-Number-of-FEC-Blocks OBJECT-TYPE
	SYNTAX      Integer32
	MAX-ACCESS  read-only
	STATUS      current
	DESCRIPTION
		""
        ::= { exc2-Param-T2-PLP-B-Column-16 9 }

exc2-Param-T2-PLP-B-Column-16-Transmission-Mode OBJECT-TYPE
	SYNTAX      INTEGER {normal (0), highEfficiency (1)}
	MAX-ACCESS  read-only
	STATUS      current
	DESCRIPTION
		""
        ::= { exc2-Param-T2-PLP-B-Column-16 10 }

exc2-Param-T2-PLP-B-Column-16-ISSY OBJECT-TYPE
	SYNTAX      INTEGER {false(0), true(1)}
	MAX-ACCESS  read-only
	STATUS      current
	DESCRIPTION
		""
        ::= { exc2-Param-T2-PLP-B-Column-16 11 }

exc2-Param-T2-PLP-B-Column-16-NULL-Packet-Deletion OBJECT-TYPE
	SYNTAX      INTEGER {false(0), true(1)}
	MAX-ACCESS  read-only
	STATUS      current
	DESCRIPTION
		""
        ::= { exc2-Param-T2-PLP-B-Column-16 12 }

exc2-Param-T2-PLP-B-Column-16-In-Band-Signaling OBJECT-TYPE
	SYNTAX      INTEGER {false(0), true(1)}
	MAX-ACCESS  read-only
	STATUS      current
	DESCRIPTION
		""
        ::= { exc2-Param-T2-PLP-B-Column-16 13 }

exc2-Param-T2-PLP-B-Column-15-PLP-ID OBJECT-TYPE
	SYNTAX      Integer32
	MAX-ACCESS  read-only
	STATUS      current
	DESCRIPTION
		""
        ::= { exc2-Param-T2-PLP-B-Column-15 1 }

exc2-Param-T2-PLP-B-Column-15-PLP-Type OBJECT-TYPE
	SYNTAX      INTEGER {common (0), type1 (1), type2 (2)}
	MAX-ACCESS  read-only
	STATUS      current
	DESCRIPTION
		""
        ::= { exc2-Param-T2-PLP-B-Column-15 2 }

exc2-Param-T2-PLP-B-Column-15-LDPC OBJECT-TYPE
	SYNTAX      INTEGER {lDPC_16K (0), lDPC_64K (1)}
	MAX-ACCESS  read-only
	STATUS      current
	DESCRIPTION
		""
        ::= { exc2-Param-T2-PLP-B-Column-15 3 }

exc2-Param-T2-PLP-B-Column-15-Coderate OBJECT-TYPE
	SYNTAX      INTEGER {rate_1_2 (0), rate_3_5 (1), rate_2_3 (2), rate_3_4 (3), rate_4_5 (4), rate_5_6 (5)}
	MAX-ACCESS  read-only
	STATUS      current
	DESCRIPTION
		""
        ::= { exc2-Param-T2-PLP-B-Column-15 4 }

exc2-Param-T2-PLP-B-Column-15-Modulation OBJECT-TYPE
	SYNTAX      INTEGER {qPSK (0), qAM_16 (1), qAM_64 (2), qAM_256 (3)}
	MAX-ACCESS  read-only
	STATUS      current
	DESCRIPTION
		""
        ::= { exc2-Param-T2-PLP-B-Column-15 5 }

exc2-Param-T2-PLP-B-Column-15-Rotated-Constellation OBJECT-TYPE
	SYNTAX      INTEGER {notUsed (0), used (1)}
	MAX-ACCESS  read-only
	STATUS      current
	DESCRIPTION
		""
        ::= { exc2-Param-T2-PLP-B-Column-15 6 }

exc2-Param-T2-PLP-B-Column-15-Time-Interleave-Type OBJECT-TYPE
	SYNTAX      INTEGER {oneT2Frame (0), severalT2Frames (1), bypassed (2)}
	MAX-ACCESS  read-only
	STATUS      current
	DESCRIPTION
		""
        ::= { exc2-Param-T2-PLP-B-Column-15 7 }

exc2-Param-T2-PLP-B-Column-15-Time-Interleave-Length OBJECT-TYPE
	SYNTAX      Integer32
	MAX-ACCESS  read-only
	STATUS      current
	DESCRIPTION
		""
        ::= { exc2-Param-T2-PLP-B-Column-15 8 }

exc2-Param-T2-PLP-B-Column-15-Number-of-FEC-Blocks OBJECT-TYPE
	SYNTAX      Integer32
	MAX-ACCESS  read-only
	STATUS      current
	DESCRIPTION
		""
        ::= { exc2-Param-T2-PLP-B-Column-15 9 }

exc2-Param-T2-PLP-B-Column-15-Transmission-Mode OBJECT-TYPE
	SYNTAX      INTEGER {normal (0), highEfficiency (1)}
	MAX-ACCESS  read-only
	STATUS      current
	DESCRIPTION
		""
        ::= { exc2-Param-T2-PLP-B-Column-15 10 }

exc2-Param-T2-PLP-B-Column-15-ISSY OBJECT-TYPE
	SYNTAX      INTEGER {false(0), true(1)}
	MAX-ACCESS  read-only
	STATUS      current
	DESCRIPTION
		""
        ::= { exc2-Param-T2-PLP-B-Column-15 11 }

exc2-Param-T2-PLP-B-Column-15-NULL-Packet-Deletion OBJECT-TYPE
	SYNTAX      INTEGER {false(0), true(1)}
	MAX-ACCESS  read-only
	STATUS      current
	DESCRIPTION
		""
        ::= { exc2-Param-T2-PLP-B-Column-15 12 }

exc2-Param-T2-PLP-B-Column-15-In-Band-Signaling OBJECT-TYPE
	SYNTAX      INTEGER {false(0), true(1)}
	MAX-ACCESS  read-only
	STATUS      current
	DESCRIPTION
		""
        ::= { exc2-Param-T2-PLP-B-Column-15 13 }

exc2-Param-T2-PLP-B-Column-14-PLP-ID OBJECT-TYPE
	SYNTAX      Integer32
	MAX-ACCESS  read-only
	STATUS      current
	DESCRIPTION
		""
        ::= { exc2-Param-T2-PLP-B-Column-14 1 }

exc2-Param-T2-PLP-B-Column-14-PLP-Type OBJECT-TYPE
	SYNTAX      INTEGER {common (0), type1 (1), type2 (2)}
	MAX-ACCESS  read-only
	STATUS      current
	DESCRIPTION
		""
        ::= { exc2-Param-T2-PLP-B-Column-14 2 }

exc2-Param-T2-PLP-B-Column-14-LDPC OBJECT-TYPE
	SYNTAX      INTEGER {lDPC_16K (0), lDPC_64K (1)}
	MAX-ACCESS  read-only
	STATUS      current
	DESCRIPTION
		""
        ::= { exc2-Param-T2-PLP-B-Column-14 3 }

exc2-Param-T2-PLP-B-Column-14-Coderate OBJECT-TYPE
	SYNTAX      INTEGER {rate_1_2 (0), rate_3_5 (1), rate_2_3 (2), rate_3_4 (3), rate_4_5 (4), rate_5_6 (5)}
	MAX-ACCESS  read-only
	STATUS      current
	DESCRIPTION
		""
        ::= { exc2-Param-T2-PLP-B-Column-14 4 }

exc2-Param-T2-PLP-B-Column-14-Modulation OBJECT-TYPE
	SYNTAX      INTEGER {qPSK (0), qAM_16 (1), qAM_64 (2), qAM_256 (3)}
	MAX-ACCESS  read-only
	STATUS      current
	DESCRIPTION
		""
        ::= { exc2-Param-T2-PLP-B-Column-14 5 }

exc2-Param-T2-PLP-B-Column-14-Rotated-Constellation OBJECT-TYPE
	SYNTAX      INTEGER {notUsed (0), used (1)}
	MAX-ACCESS  read-only
	STATUS      current
	DESCRIPTION
		""
        ::= { exc2-Param-T2-PLP-B-Column-14 6 }

exc2-Param-T2-PLP-B-Column-14-Time-Interleave-Type OBJECT-TYPE
	SYNTAX      INTEGER {oneT2Frame (0), severalT2Frames (1), bypassed (2)}
	MAX-ACCESS  read-only
	STATUS      current
	DESCRIPTION
		""
        ::= { exc2-Param-T2-PLP-B-Column-14 7 }

exc2-Param-T2-PLP-B-Column-14-Time-Interleave-Length OBJECT-TYPE
	SYNTAX      Integer32
	MAX-ACCESS  read-only
	STATUS      current
	DESCRIPTION
		""
        ::= { exc2-Param-T2-PLP-B-Column-14 8 }

exc2-Param-T2-PLP-B-Column-14-Number-of-FEC-Blocks OBJECT-TYPE
	SYNTAX      Integer32
	MAX-ACCESS  read-only
	STATUS      current
	DESCRIPTION
		""
        ::= { exc2-Param-T2-PLP-B-Column-14 9 }

exc2-Param-T2-PLP-B-Column-14-Transmission-Mode OBJECT-TYPE
	SYNTAX      INTEGER {normal (0), highEfficiency (1)}
	MAX-ACCESS  read-only
	STATUS      current
	DESCRIPTION
		""
        ::= { exc2-Param-T2-PLP-B-Column-14 10 }

exc2-Param-T2-PLP-B-Column-14-ISSY OBJECT-TYPE
	SYNTAX      INTEGER {false(0), true(1)}
	MAX-ACCESS  read-only
	STATUS      current
	DESCRIPTION
		""
        ::= { exc2-Param-T2-PLP-B-Column-14 11 }

exc2-Param-T2-PLP-B-Column-14-NULL-Packet-Deletion OBJECT-TYPE
	SYNTAX      INTEGER {false(0), true(1)}
	MAX-ACCESS  read-only
	STATUS      current
	DESCRIPTION
		""
        ::= { exc2-Param-T2-PLP-B-Column-14 12 }

exc2-Param-T2-PLP-B-Column-14-In-Band-Signaling OBJECT-TYPE
	SYNTAX      INTEGER {false(0), true(1)}
	MAX-ACCESS  read-only
	STATUS      current
	DESCRIPTION
		""
        ::= { exc2-Param-T2-PLP-B-Column-14 13 }

exc2-Param-T2-PLP-B-Column-13-PLP-ID OBJECT-TYPE
	SYNTAX      Integer32
	MAX-ACCESS  read-only
	STATUS      current
	DESCRIPTION
		""
        ::= { exc2-Param-T2-PLP-B-Column-13 1 }

exc2-Param-T2-PLP-B-Column-13-PLP-Type OBJECT-TYPE
	SYNTAX      INTEGER {common (0), type1 (1), type2 (2)}
	MAX-ACCESS  read-only
	STATUS      current
	DESCRIPTION
		""
        ::= { exc2-Param-T2-PLP-B-Column-13 2 }

exc2-Param-T2-PLP-B-Column-13-LDPC OBJECT-TYPE
	SYNTAX      INTEGER {lDPC_16K (0), lDPC_64K (1)}
	MAX-ACCESS  read-only
	STATUS      current
	DESCRIPTION
		""
        ::= { exc2-Param-T2-PLP-B-Column-13 3 }

exc2-Param-T2-PLP-B-Column-13-Coderate OBJECT-TYPE
	SYNTAX      INTEGER {rate_1_2 (0), rate_3_5 (1), rate_2_3 (2), rate_3_4 (3), rate_4_5 (4), rate_5_6 (5)}
	MAX-ACCESS  read-only
	STATUS      current
	DESCRIPTION
		""
        ::= { exc2-Param-T2-PLP-B-Column-13 4 }

exc2-Param-T2-PLP-B-Column-13-Modulation OBJECT-TYPE
	SYNTAX      INTEGER {qPSK (0), qAM_16 (1), qAM_64 (2), qAM_256 (3)}
	MAX-ACCESS  read-only
	STATUS      current
	DESCRIPTION
		""
        ::= { exc2-Param-T2-PLP-B-Column-13 5 }

exc2-Param-T2-PLP-B-Column-13-Rotated-Constellation OBJECT-TYPE
	SYNTAX      INTEGER {notUsed (0), used (1)}
	MAX-ACCESS  read-only
	STATUS      current
	DESCRIPTION
		""
        ::= { exc2-Param-T2-PLP-B-Column-13 6 }

exc2-Param-T2-PLP-B-Column-13-Time-Interleave-Type OBJECT-TYPE
	SYNTAX      INTEGER {oneT2Frame (0), severalT2Frames (1), bypassed (2)}
	MAX-ACCESS  read-only
	STATUS      current
	DESCRIPTION
		""
        ::= { exc2-Param-T2-PLP-B-Column-13 7 }

exc2-Param-T2-PLP-B-Column-13-Time-Interleave-Length OBJECT-TYPE
	SYNTAX      Integer32
	MAX-ACCESS  read-only
	STATUS      current
	DESCRIPTION
		""
        ::= { exc2-Param-T2-PLP-B-Column-13 8 }

exc2-Param-T2-PLP-B-Column-13-Number-of-FEC-Blocks OBJECT-TYPE
	SYNTAX      Integer32
	MAX-ACCESS  read-only
	STATUS      current
	DESCRIPTION
		""
        ::= { exc2-Param-T2-PLP-B-Column-13 9 }

exc2-Param-T2-PLP-B-Column-13-Transmission-Mode OBJECT-TYPE
	SYNTAX      INTEGER {normal (0), highEfficiency (1)}
	MAX-ACCESS  read-only
	STATUS      current
	DESCRIPTION
		""
        ::= { exc2-Param-T2-PLP-B-Column-13 10 }

exc2-Param-T2-PLP-B-Column-13-ISSY OBJECT-TYPE
	SYNTAX      INTEGER {false(0), true(1)}
	MAX-ACCESS  read-only
	STATUS      current
	DESCRIPTION
		""
        ::= { exc2-Param-T2-PLP-B-Column-13 11 }

exc2-Param-T2-PLP-B-Column-13-NULL-Packet-Deletion OBJECT-TYPE
	SYNTAX      INTEGER {false(0), true(1)}
	MAX-ACCESS  read-only
	STATUS      current
	DESCRIPTION
		""
        ::= { exc2-Param-T2-PLP-B-Column-13 12 }

exc2-Param-T2-PLP-B-Column-13-In-Band-Signaling OBJECT-TYPE
	SYNTAX      INTEGER {false(0), true(1)}
	MAX-ACCESS  read-only
	STATUS      current
	DESCRIPTION
		""
        ::= { exc2-Param-T2-PLP-B-Column-13 13 }

exc2-Param-T2-PLP-B-Column-12-PLP-ID OBJECT-TYPE
	SYNTAX      Integer32
	MAX-ACCESS  read-only
	STATUS      current
	DESCRIPTION
		""
        ::= { exc2-Param-T2-PLP-B-Column-12 1 }

exc2-Param-T2-PLP-B-Column-12-PLP-Type OBJECT-TYPE
	SYNTAX      INTEGER {common (0), type1 (1), type2 (2)}
	MAX-ACCESS  read-only
	STATUS      current
	DESCRIPTION
		""
        ::= { exc2-Param-T2-PLP-B-Column-12 2 }

exc2-Param-T2-PLP-B-Column-12-LDPC OBJECT-TYPE
	SYNTAX      INTEGER {lDPC_16K (0), lDPC_64K (1)}
	MAX-ACCESS  read-only
	STATUS      current
	DESCRIPTION
		""
        ::= { exc2-Param-T2-PLP-B-Column-12 3 }

exc2-Param-T2-PLP-B-Column-12-Coderate OBJECT-TYPE
	SYNTAX      INTEGER {rate_1_2 (0), rate_3_5 (1), rate_2_3 (2), rate_3_4 (3), rate_4_5 (4), rate_5_6 (5)}
	MAX-ACCESS  read-only
	STATUS      current
	DESCRIPTION
		""
        ::= { exc2-Param-T2-PLP-B-Column-12 4 }

exc2-Param-T2-PLP-B-Column-12-Modulation OBJECT-TYPE
	SYNTAX      INTEGER {qPSK (0), qAM_16 (1), qAM_64 (2), qAM_256 (3)}
	MAX-ACCESS  read-only
	STATUS      current
	DESCRIPTION
		""
        ::= { exc2-Param-T2-PLP-B-Column-12 5 }

exc2-Param-T2-PLP-B-Column-12-Rotated-Constellation OBJECT-TYPE
	SYNTAX      INTEGER {notUsed (0), used (1)}
	MAX-ACCESS  read-only
	STATUS      current
	DESCRIPTION
		""
        ::= { exc2-Param-T2-PLP-B-Column-12 6 }

exc2-Param-T2-PLP-B-Column-12-Time-Interleave-Type OBJECT-TYPE
	SYNTAX      INTEGER {oneT2Frame (0), severalT2Frames (1), bypassed (2)}
	MAX-ACCESS  read-only
	STATUS      current
	DESCRIPTION
		""
        ::= { exc2-Param-T2-PLP-B-Column-12 7 }

exc2-Param-T2-PLP-B-Column-12-Time-Interleave-Length OBJECT-TYPE
	SYNTAX      Integer32
	MAX-ACCESS  read-only
	STATUS      current
	DESCRIPTION
		""
        ::= { exc2-Param-T2-PLP-B-Column-12 8 }

exc2-Param-T2-PLP-B-Column-12-Number-of-FEC-Blocks OBJECT-TYPE
	SYNTAX      Integer32
	MAX-ACCESS  read-only
	STATUS      current
	DESCRIPTION
		""
        ::= { exc2-Param-T2-PLP-B-Column-12 9 }

exc2-Param-T2-PLP-B-Column-12-Transmission-Mode OBJECT-TYPE
	SYNTAX      INTEGER {normal (0), highEfficiency (1)}
	MAX-ACCESS  read-only
	STATUS      current
	DESCRIPTION
		""
        ::= { exc2-Param-T2-PLP-B-Column-12 10 }

exc2-Param-T2-PLP-B-Column-12-ISSY OBJECT-TYPE
	SYNTAX      INTEGER {false(0), true(1)}
	MAX-ACCESS  read-only
	STATUS      current
	DESCRIPTION
		""
        ::= { exc2-Param-T2-PLP-B-Column-12 11 }

exc2-Param-T2-PLP-B-Column-12-NULL-Packet-Deletion OBJECT-TYPE
	SYNTAX      INTEGER {false(0), true(1)}
	MAX-ACCESS  read-only
	STATUS      current
	DESCRIPTION
		""
        ::= { exc2-Param-T2-PLP-B-Column-12 12 }

exc2-Param-T2-PLP-B-Column-12-In-Band-Signaling OBJECT-TYPE
	SYNTAX      INTEGER {false(0), true(1)}
	MAX-ACCESS  read-only
	STATUS      current
	DESCRIPTION
		""
        ::= { exc2-Param-T2-PLP-B-Column-12 13 }

exc2-Param-T2-PLP-B-Column-11-PLP-ID OBJECT-TYPE
	SYNTAX      Integer32
	MAX-ACCESS  read-only
	STATUS      current
	DESCRIPTION
		""
        ::= { exc2-Param-T2-PLP-B-Column-11 1 }

exc2-Param-T2-PLP-B-Column-11-PLP-Type OBJECT-TYPE
	SYNTAX      INTEGER {common (0), type1 (1), type2 (2)}
	MAX-ACCESS  read-only
	STATUS      current
	DESCRIPTION
		""
        ::= { exc2-Param-T2-PLP-B-Column-11 2 }

exc2-Param-T2-PLP-B-Column-11-LDPC OBJECT-TYPE
	SYNTAX      INTEGER {lDPC_16K (0), lDPC_64K (1)}
	MAX-ACCESS  read-only
	STATUS      current
	DESCRIPTION
		""
        ::= { exc2-Param-T2-PLP-B-Column-11 3 }

exc2-Param-T2-PLP-B-Column-11-Coderate OBJECT-TYPE
	SYNTAX      INTEGER {rate_1_2 (0), rate_3_5 (1), rate_2_3 (2), rate_3_4 (3), rate_4_5 (4), rate_5_6 (5)}
	MAX-ACCESS  read-only
	STATUS      current
	DESCRIPTION
		""
        ::= { exc2-Param-T2-PLP-B-Column-11 4 }

exc2-Param-T2-PLP-B-Column-11-Modulation OBJECT-TYPE
	SYNTAX      INTEGER {qPSK (0), qAM_16 (1), qAM_64 (2), qAM_256 (3)}
	MAX-ACCESS  read-only
	STATUS      current
	DESCRIPTION
		""
        ::= { exc2-Param-T2-PLP-B-Column-11 5 }

exc2-Param-T2-PLP-B-Column-11-Rotated-Constellation OBJECT-TYPE
	SYNTAX      INTEGER {notUsed (0), used (1)}
	MAX-ACCESS  read-only
	STATUS      current
	DESCRIPTION
		""
        ::= { exc2-Param-T2-PLP-B-Column-11 6 }

exc2-Param-T2-PLP-B-Column-11-Time-Interleave-Type OBJECT-TYPE
	SYNTAX      INTEGER {oneT2Frame (0), severalT2Frames (1), bypassed (2)}
	MAX-ACCESS  read-only
	STATUS      current
	DESCRIPTION
		""
        ::= { exc2-Param-T2-PLP-B-Column-11 7 }

exc2-Param-T2-PLP-B-Column-11-Time-Interleave-Length OBJECT-TYPE
	SYNTAX      Integer32
	MAX-ACCESS  read-only
	STATUS      current
	DESCRIPTION
		""
        ::= { exc2-Param-T2-PLP-B-Column-11 8 }

exc2-Param-T2-PLP-B-Column-11-Number-of-FEC-Blocks OBJECT-TYPE
	SYNTAX      Integer32
	MAX-ACCESS  read-only
	STATUS      current
	DESCRIPTION
		""
        ::= { exc2-Param-T2-PLP-B-Column-11 9 }

exc2-Param-T2-PLP-B-Column-11-Transmission-Mode OBJECT-TYPE
	SYNTAX      INTEGER {normal (0), highEfficiency (1)}
	MAX-ACCESS  read-only
	STATUS      current
	DESCRIPTION
		""
        ::= { exc2-Param-T2-PLP-B-Column-11 10 }

exc2-Param-T2-PLP-B-Column-11-ISSY OBJECT-TYPE
	SYNTAX      INTEGER {false(0), true(1)}
	MAX-ACCESS  read-only
	STATUS      current
	DESCRIPTION
		""
        ::= { exc2-Param-T2-PLP-B-Column-11 11 }

exc2-Param-T2-PLP-B-Column-11-NULL-Packet-Deletion OBJECT-TYPE
	SYNTAX      INTEGER {false(0), true(1)}
	MAX-ACCESS  read-only
	STATUS      current
	DESCRIPTION
		""
        ::= { exc2-Param-T2-PLP-B-Column-11 12 }

exc2-Param-T2-PLP-B-Column-11-In-Band-Signaling OBJECT-TYPE
	SYNTAX      INTEGER {false(0), true(1)}
	MAX-ACCESS  read-only
	STATUS      current
	DESCRIPTION
		""
        ::= { exc2-Param-T2-PLP-B-Column-11 13 }

exc2-Param-T2-PLP-B-Column-10-PLP-ID OBJECT-TYPE
	SYNTAX      Integer32
	MAX-ACCESS  read-only
	STATUS      current
	DESCRIPTION
		""
        ::= { exc2-Param-T2-PLP-B-Column-10 1 }

exc2-Param-T2-PLP-B-Column-10-PLP-Type OBJECT-TYPE
	SYNTAX      INTEGER {common (0), type1 (1), type2 (2)}
	MAX-ACCESS  read-only
	STATUS      current
	DESCRIPTION
		""
        ::= { exc2-Param-T2-PLP-B-Column-10 2 }

exc2-Param-T2-PLP-B-Column-10-LDPC OBJECT-TYPE
	SYNTAX      INTEGER {lDPC_16K (0), lDPC_64K (1)}
	MAX-ACCESS  read-only
	STATUS      current
	DESCRIPTION
		""
        ::= { exc2-Param-T2-PLP-B-Column-10 3 }

exc2-Param-T2-PLP-B-Column-10-Coderate OBJECT-TYPE
	SYNTAX      INTEGER {rate_1_2 (0), rate_3_5 (1), rate_2_3 (2), rate_3_4 (3), rate_4_5 (4), rate_5_6 (5)}
	MAX-ACCESS  read-only
	STATUS      current
	DESCRIPTION
		""
        ::= { exc2-Param-T2-PLP-B-Column-10 4 }

exc2-Param-T2-PLP-B-Column-10-Modulation OBJECT-TYPE
	SYNTAX      INTEGER {qPSK (0), qAM_16 (1), qAM_64 (2), qAM_256 (3)}
	MAX-ACCESS  read-only
	STATUS      current
	DESCRIPTION
		""
        ::= { exc2-Param-T2-PLP-B-Column-10 5 }

exc2-Param-T2-PLP-B-Column-10-Rotated-Constellation OBJECT-TYPE
	SYNTAX      INTEGER {notUsed (0), used (1)}
	MAX-ACCESS  read-only
	STATUS      current
	DESCRIPTION
		""
        ::= { exc2-Param-T2-PLP-B-Column-10 6 }

exc2-Param-T2-PLP-B-Column-10-Time-Interleave-Type OBJECT-TYPE
	SYNTAX      INTEGER {oneT2Frame (0), severalT2Frames (1), bypassed (2)}
	MAX-ACCESS  read-only
	STATUS      current
	DESCRIPTION
		""
        ::= { exc2-Param-T2-PLP-B-Column-10 7 }

exc2-Param-T2-PLP-B-Column-10-Time-Interleave-Length OBJECT-TYPE
	SYNTAX      Integer32
	MAX-ACCESS  read-only
	STATUS      current
	DESCRIPTION
		""
        ::= { exc2-Param-T2-PLP-B-Column-10 8 }

exc2-Param-T2-PLP-B-Column-10-Number-of-FEC-Blocks OBJECT-TYPE
	SYNTAX      Integer32
	MAX-ACCESS  read-only
	STATUS      current
	DESCRIPTION
		""
        ::= { exc2-Param-T2-PLP-B-Column-10 9 }

exc2-Param-T2-PLP-B-Column-10-Transmission-Mode OBJECT-TYPE
	SYNTAX      INTEGER {normal (0), highEfficiency (1)}
	MAX-ACCESS  read-only
	STATUS      current
	DESCRIPTION
		""
        ::= { exc2-Param-T2-PLP-B-Column-10 10 }

exc2-Param-T2-PLP-B-Column-10-ISSY OBJECT-TYPE
	SYNTAX      INTEGER {false(0), true(1)}
	MAX-ACCESS  read-only
	STATUS      current
	DESCRIPTION
		""
        ::= { exc2-Param-T2-PLP-B-Column-10 11 }

exc2-Param-T2-PLP-B-Column-10-NULL-Packet-Deletion OBJECT-TYPE
	SYNTAX      INTEGER {false(0), true(1)}
	MAX-ACCESS  read-only
	STATUS      current
	DESCRIPTION
		""
        ::= { exc2-Param-T2-PLP-B-Column-10 12 }

exc2-Param-T2-PLP-B-Column-10-In-Band-Signaling OBJECT-TYPE
	SYNTAX      INTEGER {false(0), true(1)}
	MAX-ACCESS  read-only
	STATUS      current
	DESCRIPTION
		""
        ::= { exc2-Param-T2-PLP-B-Column-10 13 }

exc2-Param-T2-PLP-B-Column-9-PLP-ID OBJECT-TYPE
	SYNTAX      Integer32
	MAX-ACCESS  read-only
	STATUS      current
	DESCRIPTION
		""
        ::= { exc2-Param-T2-PLP-B-Column-9 1 }

exc2-Param-T2-PLP-B-Column-9-PLP-Type OBJECT-TYPE
	SYNTAX      INTEGER {common (0), type1 (1), type2 (2)}
	MAX-ACCESS  read-only
	STATUS      current
	DESCRIPTION
		""
        ::= { exc2-Param-T2-PLP-B-Column-9 2 }

exc2-Param-T2-PLP-B-Column-9-LDPC OBJECT-TYPE
	SYNTAX      INTEGER {lDPC_16K (0), lDPC_64K (1)}
	MAX-ACCESS  read-only
	STATUS      current
	DESCRIPTION
		""
        ::= { exc2-Param-T2-PLP-B-Column-9 3 }

exc2-Param-T2-PLP-B-Column-9-Coderate OBJECT-TYPE
	SYNTAX      INTEGER {rate_1_2 (0), rate_3_5 (1), rate_2_3 (2), rate_3_4 (3), rate_4_5 (4), rate_5_6 (5)}
	MAX-ACCESS  read-only
	STATUS      current
	DESCRIPTION
		""
        ::= { exc2-Param-T2-PLP-B-Column-9 4 }

exc2-Param-T2-PLP-B-Column-9-Modulation OBJECT-TYPE
	SYNTAX      INTEGER {qPSK (0), qAM_16 (1), qAM_64 (2), qAM_256 (3)}
	MAX-ACCESS  read-only
	STATUS      current
	DESCRIPTION
		""
        ::= { exc2-Param-T2-PLP-B-Column-9 5 }

exc2-Param-T2-PLP-B-Column-9-Rotated-Constellation OBJECT-TYPE
	SYNTAX      INTEGER {notUsed (0), used (1)}
	MAX-ACCESS  read-only
	STATUS      current
	DESCRIPTION
		""
        ::= { exc2-Param-T2-PLP-B-Column-9 6 }

exc2-Param-T2-PLP-B-Column-9-Time-Interleave-Type OBJECT-TYPE
	SYNTAX      INTEGER {oneT2Frame (0), severalT2Frames (1), bypassed (2)}
	MAX-ACCESS  read-only
	STATUS      current
	DESCRIPTION
		""
        ::= { exc2-Param-T2-PLP-B-Column-9 7 }

exc2-Param-T2-PLP-B-Column-9-Time-Interleave-Length OBJECT-TYPE
	SYNTAX      Integer32
	MAX-ACCESS  read-only
	STATUS      current
	DESCRIPTION
		""
        ::= { exc2-Param-T2-PLP-B-Column-9 8 }

exc2-Param-T2-PLP-B-Column-9-Number-of-FEC-Blocks OBJECT-TYPE
	SYNTAX      Integer32
	MAX-ACCESS  read-only
	STATUS      current
	DESCRIPTION
		""
        ::= { exc2-Param-T2-PLP-B-Column-9 9 }

exc2-Param-T2-PLP-B-Column-9-Transmission-Mode OBJECT-TYPE
	SYNTAX      INTEGER {normal (0), highEfficiency (1)}
	MAX-ACCESS  read-only
	STATUS      current
	DESCRIPTION
		""
        ::= { exc2-Param-T2-PLP-B-Column-9 10 }

exc2-Param-T2-PLP-B-Column-9-ISSY OBJECT-TYPE
	SYNTAX      INTEGER {false(0), true(1)}
	MAX-ACCESS  read-only
	STATUS      current
	DESCRIPTION
		""
        ::= { exc2-Param-T2-PLP-B-Column-9 11 }

exc2-Param-T2-PLP-B-Column-9-NULL-Packet-Deletion OBJECT-TYPE
	SYNTAX      INTEGER {false(0), true(1)}
	MAX-ACCESS  read-only
	STATUS      current
	DESCRIPTION
		""
        ::= { exc2-Param-T2-PLP-B-Column-9 12 }

exc2-Param-T2-PLP-B-Column-9-In-Band-Signaling OBJECT-TYPE
	SYNTAX      INTEGER {false(0), true(1)}
	MAX-ACCESS  read-only
	STATUS      current
	DESCRIPTION
		""
        ::= { exc2-Param-T2-PLP-B-Column-9 13 }

exc2-Param-T2-PLP-B-Column-8-PLP-ID OBJECT-TYPE
	SYNTAX      Integer32
	MAX-ACCESS  read-only
	STATUS      current
	DESCRIPTION
		""
        ::= { exc2-Param-T2-PLP-B-Column-8 1 }

exc2-Param-T2-PLP-B-Column-8-PLP-Type OBJECT-TYPE
	SYNTAX      INTEGER {common (0), type1 (1), type2 (2)}
	MAX-ACCESS  read-only
	STATUS      current
	DESCRIPTION
		""
        ::= { exc2-Param-T2-PLP-B-Column-8 2 }

exc2-Param-T2-PLP-B-Column-8-LDPC OBJECT-TYPE
	SYNTAX      INTEGER {lDPC_16K (0), lDPC_64K (1)}
	MAX-ACCESS  read-only
	STATUS      current
	DESCRIPTION
		""
        ::= { exc2-Param-T2-PLP-B-Column-8 3 }

exc2-Param-T2-PLP-B-Column-8-Coderate OBJECT-TYPE
	SYNTAX      INTEGER {rate_1_2 (0), rate_3_5 (1), rate_2_3 (2), rate_3_4 (3), rate_4_5 (4), rate_5_6 (5)}
	MAX-ACCESS  read-only
	STATUS      current
	DESCRIPTION
		""
        ::= { exc2-Param-T2-PLP-B-Column-8 4 }

exc2-Param-T2-PLP-B-Column-8-Modulation OBJECT-TYPE
	SYNTAX      INTEGER {qPSK (0), qAM_16 (1), qAM_64 (2), qAM_256 (3)}
	MAX-ACCESS  read-only
	STATUS      current
	DESCRIPTION
		""
        ::= { exc2-Param-T2-PLP-B-Column-8 5 }

exc2-Param-T2-PLP-B-Column-8-Rotated-Constellation OBJECT-TYPE
	SYNTAX      INTEGER {notUsed (0), used (1)}
	MAX-ACCESS  read-only
	STATUS      current
	DESCRIPTION
		""
        ::= { exc2-Param-T2-PLP-B-Column-8 6 }

exc2-Param-T2-PLP-B-Column-8-Time-Interleave-Type OBJECT-TYPE
	SYNTAX      INTEGER {oneT2Frame (0), severalT2Frames (1), bypassed (2)}
	MAX-ACCESS  read-only
	STATUS      current
	DESCRIPTION
		""
        ::= { exc2-Param-T2-PLP-B-Column-8 7 }

exc2-Param-T2-PLP-B-Column-8-Time-Interleave-Length OBJECT-TYPE
	SYNTAX      Integer32
	MAX-ACCESS  read-only
	STATUS      current
	DESCRIPTION
		""
        ::= { exc2-Param-T2-PLP-B-Column-8 8 }

exc2-Param-T2-PLP-B-Column-8-Number-of-FEC-Blocks OBJECT-TYPE
	SYNTAX      Integer32
	MAX-ACCESS  read-only
	STATUS      current
	DESCRIPTION
		""
        ::= { exc2-Param-T2-PLP-B-Column-8 9 }

exc2-Param-T2-PLP-B-Column-8-Transmission-Mode OBJECT-TYPE
	SYNTAX      INTEGER {normal (0), highEfficiency (1)}
	MAX-ACCESS  read-only
	STATUS      current
	DESCRIPTION
		""
        ::= { exc2-Param-T2-PLP-B-Column-8 10 }

exc2-Param-T2-PLP-B-Column-8-ISSY OBJECT-TYPE
	SYNTAX      INTEGER {false(0), true(1)}
	MAX-ACCESS  read-only
	STATUS      current
	DESCRIPTION
		""
        ::= { exc2-Param-T2-PLP-B-Column-8 11 }

exc2-Param-T2-PLP-B-Column-8-NULL-Packet-Deletion OBJECT-TYPE
	SYNTAX      INTEGER {false(0), true(1)}
	MAX-ACCESS  read-only
	STATUS      current
	DESCRIPTION
		""
        ::= { exc2-Param-T2-PLP-B-Column-8 12 }

exc2-Param-T2-PLP-B-Column-8-In-Band-Signaling OBJECT-TYPE
	SYNTAX      INTEGER {false(0), true(1)}
	MAX-ACCESS  read-only
	STATUS      current
	DESCRIPTION
		""
        ::= { exc2-Param-T2-PLP-B-Column-8 13 }

exc2-Param-T2-PLP-B-Column-7-PLP-ID OBJECT-TYPE
	SYNTAX      Integer32
	MAX-ACCESS  read-only
	STATUS      current
	DESCRIPTION
		""
        ::= { exc2-Param-T2-PLP-B-Column-7 1 }

exc2-Param-T2-PLP-B-Column-7-PLP-Type OBJECT-TYPE
	SYNTAX      INTEGER {common (0), type1 (1), type2 (2)}
	MAX-ACCESS  read-only
	STATUS      current
	DESCRIPTION
		""
        ::= { exc2-Param-T2-PLP-B-Column-7 2 }

exc2-Param-T2-PLP-B-Column-7-LDPC OBJECT-TYPE
	SYNTAX      INTEGER {lDPC_16K (0), lDPC_64K (1)}
	MAX-ACCESS  read-only
	STATUS      current
	DESCRIPTION
		""
        ::= { exc2-Param-T2-PLP-B-Column-7 3 }

exc2-Param-T2-PLP-B-Column-7-Coderate OBJECT-TYPE
	SYNTAX      INTEGER {rate_1_2 (0), rate_3_5 (1), rate_2_3 (2), rate_3_4 (3), rate_4_5 (4), rate_5_6 (5)}
	MAX-ACCESS  read-only
	STATUS      current
	DESCRIPTION
		""
        ::= { exc2-Param-T2-PLP-B-Column-7 4 }

exc2-Param-T2-PLP-B-Column-7-Modulation OBJECT-TYPE
	SYNTAX      INTEGER {qPSK (0), qAM_16 (1), qAM_64 (2), qAM_256 (3)}
	MAX-ACCESS  read-only
	STATUS      current
	DESCRIPTION
		""
        ::= { exc2-Param-T2-PLP-B-Column-7 5 }

exc2-Param-T2-PLP-B-Column-7-Rotated-Constellation OBJECT-TYPE
	SYNTAX      INTEGER {notUsed (0), used (1)}
	MAX-ACCESS  read-only
	STATUS      current
	DESCRIPTION
		""
        ::= { exc2-Param-T2-PLP-B-Column-7 6 }

exc2-Param-T2-PLP-B-Column-7-Time-Interleave-Type OBJECT-TYPE
	SYNTAX      INTEGER {oneT2Frame (0), severalT2Frames (1), bypassed (2)}
	MAX-ACCESS  read-only
	STATUS      current
	DESCRIPTION
		""
        ::= { exc2-Param-T2-PLP-B-Column-7 7 }

exc2-Param-T2-PLP-B-Column-7-Time-Interleave-Length OBJECT-TYPE
	SYNTAX      Integer32
	MAX-ACCESS  read-only
	STATUS      current
	DESCRIPTION
		""
        ::= { exc2-Param-T2-PLP-B-Column-7 8 }

exc2-Param-T2-PLP-B-Column-7-Number-of-FEC-Blocks OBJECT-TYPE
	SYNTAX      Integer32
	MAX-ACCESS  read-only
	STATUS      current
	DESCRIPTION
		""
        ::= { exc2-Param-T2-PLP-B-Column-7 9 }

exc2-Param-T2-PLP-B-Column-7-Transmission-Mode OBJECT-TYPE
	SYNTAX      INTEGER {normal (0), highEfficiency (1)}
	MAX-ACCESS  read-only
	STATUS      current
	DESCRIPTION
		""
        ::= { exc2-Param-T2-PLP-B-Column-7 10 }

exc2-Param-T2-PLP-B-Column-7-ISSY OBJECT-TYPE
	SYNTAX      INTEGER {false(0), true(1)}
	MAX-ACCESS  read-only
	STATUS      current
	DESCRIPTION
		""
        ::= { exc2-Param-T2-PLP-B-Column-7 11 }

exc2-Param-T2-PLP-B-Column-7-NULL-Packet-Deletion OBJECT-TYPE
	SYNTAX      INTEGER {false(0), true(1)}
	MAX-ACCESS  read-only
	STATUS      current
	DESCRIPTION
		""
        ::= { exc2-Param-T2-PLP-B-Column-7 12 }

exc2-Param-T2-PLP-B-Column-7-In-Band-Signaling OBJECT-TYPE
	SYNTAX      INTEGER {false(0), true(1)}
	MAX-ACCESS  read-only
	STATUS      current
	DESCRIPTION
		""
        ::= { exc2-Param-T2-PLP-B-Column-7 13 }

exc2-Param-T2-PLP-B-Column-6-PLP-ID OBJECT-TYPE
	SYNTAX      Integer32
	MAX-ACCESS  read-only
	STATUS      current
	DESCRIPTION
		""
        ::= { exc2-Param-T2-PLP-B-Column-6 1 }

exc2-Param-T2-PLP-B-Column-6-PLP-Type OBJECT-TYPE
	SYNTAX      INTEGER {common (0), type1 (1), type2 (2)}
	MAX-ACCESS  read-only
	STATUS      current
	DESCRIPTION
		""
        ::= { exc2-Param-T2-PLP-B-Column-6 2 }

exc2-Param-T2-PLP-B-Column-6-LDPC OBJECT-TYPE
	SYNTAX      INTEGER {lDPC_16K (0), lDPC_64K (1)}
	MAX-ACCESS  read-only
	STATUS      current
	DESCRIPTION
		""
        ::= { exc2-Param-T2-PLP-B-Column-6 3 }

exc2-Param-T2-PLP-B-Column-6-Coderate OBJECT-TYPE
	SYNTAX      INTEGER {rate_1_2 (0), rate_3_5 (1), rate_2_3 (2), rate_3_4 (3), rate_4_5 (4), rate_5_6 (5)}
	MAX-ACCESS  read-only
	STATUS      current
	DESCRIPTION
		""
        ::= { exc2-Param-T2-PLP-B-Column-6 4 }

exc2-Param-T2-PLP-B-Column-6-Modulation OBJECT-TYPE
	SYNTAX      INTEGER {qPSK (0), qAM_16 (1), qAM_64 (2), qAM_256 (3)}
	MAX-ACCESS  read-only
	STATUS      current
	DESCRIPTION
		""
        ::= { exc2-Param-T2-PLP-B-Column-6 5 }

exc2-Param-T2-PLP-B-Column-6-Rotated-Constellation OBJECT-TYPE
	SYNTAX      INTEGER {notUsed (0), used (1)}
	MAX-ACCESS  read-only
	STATUS      current
	DESCRIPTION
		""
        ::= { exc2-Param-T2-PLP-B-Column-6 6 }

exc2-Param-T2-PLP-B-Column-6-Time-Interleave-Type OBJECT-TYPE
	SYNTAX      INTEGER {oneT2Frame (0), severalT2Frames (1), bypassed (2)}
	MAX-ACCESS  read-only
	STATUS      current
	DESCRIPTION
		""
        ::= { exc2-Param-T2-PLP-B-Column-6 7 }

exc2-Param-T2-PLP-B-Column-6-Time-Interleave-Length OBJECT-TYPE
	SYNTAX      Integer32
	MAX-ACCESS  read-only
	STATUS      current
	DESCRIPTION
		""
        ::= { exc2-Param-T2-PLP-B-Column-6 8 }

exc2-Param-T2-PLP-B-Column-6-Number-of-FEC-Blocks OBJECT-TYPE
	SYNTAX      Integer32
	MAX-ACCESS  read-only
	STATUS      current
	DESCRIPTION
		""
        ::= { exc2-Param-T2-PLP-B-Column-6 9 }

exc2-Param-T2-PLP-B-Column-6-Transmission-Mode OBJECT-TYPE
	SYNTAX      INTEGER {normal (0), highEfficiency (1)}
	MAX-ACCESS  read-only
	STATUS      current
	DESCRIPTION
		""
        ::= { exc2-Param-T2-PLP-B-Column-6 10 }

exc2-Param-T2-PLP-B-Column-6-ISSY OBJECT-TYPE
	SYNTAX      INTEGER {false(0), true(1)}
	MAX-ACCESS  read-only
	STATUS      current
	DESCRIPTION
		""
        ::= { exc2-Param-T2-PLP-B-Column-6 11 }

exc2-Param-T2-PLP-B-Column-6-NULL-Packet-Deletion OBJECT-TYPE
	SYNTAX      INTEGER {false(0), true(1)}
	MAX-ACCESS  read-only
	STATUS      current
	DESCRIPTION
		""
        ::= { exc2-Param-T2-PLP-B-Column-6 12 }

exc2-Param-T2-PLP-B-Column-6-In-Band-Signaling OBJECT-TYPE
	SYNTAX      INTEGER {false(0), true(1)}
	MAX-ACCESS  read-only
	STATUS      current
	DESCRIPTION
		""
        ::= { exc2-Param-T2-PLP-B-Column-6 13 }

exc2-Param-T2-PLP-B-Column-5-PLP-ID OBJECT-TYPE
	SYNTAX      Integer32
	MAX-ACCESS  read-only
	STATUS      current
	DESCRIPTION
		""
        ::= { exc2-Param-T2-PLP-B-Column-5 1 }

exc2-Param-T2-PLP-B-Column-5-PLP-Type OBJECT-TYPE
	SYNTAX      INTEGER {common (0), type1 (1), type2 (2)}
	MAX-ACCESS  read-only
	STATUS      current
	DESCRIPTION
		""
        ::= { exc2-Param-T2-PLP-B-Column-5 2 }

exc2-Param-T2-PLP-B-Column-5-LDPC OBJECT-TYPE
	SYNTAX      INTEGER {lDPC_16K (0), lDPC_64K (1)}
	MAX-ACCESS  read-only
	STATUS      current
	DESCRIPTION
		""
        ::= { exc2-Param-T2-PLP-B-Column-5 3 }

exc2-Param-T2-PLP-B-Column-5-Coderate OBJECT-TYPE
	SYNTAX      INTEGER {rate_1_2 (0), rate_3_5 (1), rate_2_3 (2), rate_3_4 (3), rate_4_5 (4), rate_5_6 (5)}
	MAX-ACCESS  read-only
	STATUS      current
	DESCRIPTION
		""
        ::= { exc2-Param-T2-PLP-B-Column-5 4 }

exc2-Param-T2-PLP-B-Column-5-Modulation OBJECT-TYPE
	SYNTAX      INTEGER {qPSK (0), qAM_16 (1), qAM_64 (2), qAM_256 (3)}
	MAX-ACCESS  read-only
	STATUS      current
	DESCRIPTION
		""
        ::= { exc2-Param-T2-PLP-B-Column-5 5 }

exc2-Param-T2-PLP-B-Column-5-Rotated-Constellation OBJECT-TYPE
	SYNTAX      INTEGER {notUsed (0), used (1)}
	MAX-ACCESS  read-only
	STATUS      current
	DESCRIPTION
		""
        ::= { exc2-Param-T2-PLP-B-Column-5 6 }

exc2-Param-T2-PLP-B-Column-5-Time-Interleave-Type OBJECT-TYPE
	SYNTAX      INTEGER {oneT2Frame (0), severalT2Frames (1), bypassed (2)}
	MAX-ACCESS  read-only
	STATUS      current
	DESCRIPTION
		""
        ::= { exc2-Param-T2-PLP-B-Column-5 7 }

exc2-Param-T2-PLP-B-Column-5-Time-Interleave-Length OBJECT-TYPE
	SYNTAX      Integer32
	MAX-ACCESS  read-only
	STATUS      current
	DESCRIPTION
		""
        ::= { exc2-Param-T2-PLP-B-Column-5 8 }

exc2-Param-T2-PLP-B-Column-5-Number-of-FEC-Blocks OBJECT-TYPE
	SYNTAX      Integer32
	MAX-ACCESS  read-only
	STATUS      current
	DESCRIPTION
		""
        ::= { exc2-Param-T2-PLP-B-Column-5 9 }

exc2-Param-T2-PLP-B-Column-5-Transmission-Mode OBJECT-TYPE
	SYNTAX      INTEGER {normal (0), highEfficiency (1)}
	MAX-ACCESS  read-only
	STATUS      current
	DESCRIPTION
		""
        ::= { exc2-Param-T2-PLP-B-Column-5 10 }

exc2-Param-T2-PLP-B-Column-5-ISSY OBJECT-TYPE
	SYNTAX      INTEGER {false(0), true(1)}
	MAX-ACCESS  read-only
	STATUS      current
	DESCRIPTION
		""
        ::= { exc2-Param-T2-PLP-B-Column-5 11 }

exc2-Param-T2-PLP-B-Column-5-NULL-Packet-Deletion OBJECT-TYPE
	SYNTAX      INTEGER {false(0), true(1)}
	MAX-ACCESS  read-only
	STATUS      current
	DESCRIPTION
		""
        ::= { exc2-Param-T2-PLP-B-Column-5 12 }

exc2-Param-T2-PLP-B-Column-5-In-Band-Signaling OBJECT-TYPE
	SYNTAX      INTEGER {false(0), true(1)}
	MAX-ACCESS  read-only
	STATUS      current
	DESCRIPTION
		""
        ::= { exc2-Param-T2-PLP-B-Column-5 13 }

exc2-Param-T2-PLP-B-Column-4-PLP-ID OBJECT-TYPE
	SYNTAX      Integer32
	MAX-ACCESS  read-only
	STATUS      current
	DESCRIPTION
		""
        ::= { exc2-Param-T2-PLP-B-Column-4 1 }

exc2-Param-T2-PLP-B-Column-4-PLP-Type OBJECT-TYPE
	SYNTAX      INTEGER {common (0), type1 (1), type2 (2)}
	MAX-ACCESS  read-only
	STATUS      current
	DESCRIPTION
		""
        ::= { exc2-Param-T2-PLP-B-Column-4 2 }

exc2-Param-T2-PLP-B-Column-4-LDPC OBJECT-TYPE
	SYNTAX      INTEGER {lDPC_16K (0), lDPC_64K (1)}
	MAX-ACCESS  read-only
	STATUS      current
	DESCRIPTION
		""
        ::= { exc2-Param-T2-PLP-B-Column-4 3 }

exc2-Param-T2-PLP-B-Column-4-Coderate OBJECT-TYPE
	SYNTAX      INTEGER {rate_1_2 (0), rate_3_5 (1), rate_2_3 (2), rate_3_4 (3), rate_4_5 (4), rate_5_6 (5)}
	MAX-ACCESS  read-only
	STATUS      current
	DESCRIPTION
		""
        ::= { exc2-Param-T2-PLP-B-Column-4 4 }

exc2-Param-T2-PLP-B-Column-4-Modulation OBJECT-TYPE
	SYNTAX      INTEGER {qPSK (0), qAM_16 (1), qAM_64 (2), qAM_256 (3)}
	MAX-ACCESS  read-only
	STATUS      current
	DESCRIPTION
		""
        ::= { exc2-Param-T2-PLP-B-Column-4 5 }

exc2-Param-T2-PLP-B-Column-4-Rotated-Constellation OBJECT-TYPE
	SYNTAX      INTEGER {notUsed (0), used (1)}
	MAX-ACCESS  read-only
	STATUS      current
	DESCRIPTION
		""
        ::= { exc2-Param-T2-PLP-B-Column-4 6 }

exc2-Param-T2-PLP-B-Column-4-Time-Interleave-Type OBJECT-TYPE
	SYNTAX      INTEGER {oneT2Frame (0), severalT2Frames (1), bypassed (2)}
	MAX-ACCESS  read-only
	STATUS      current
	DESCRIPTION
		""
        ::= { exc2-Param-T2-PLP-B-Column-4 7 }

exc2-Param-T2-PLP-B-Column-4-Time-Interleave-Length OBJECT-TYPE
	SYNTAX      Integer32
	MAX-ACCESS  read-only
	STATUS      current
	DESCRIPTION
		""
        ::= { exc2-Param-T2-PLP-B-Column-4 8 }

exc2-Param-T2-PLP-B-Column-4-Number-of-FEC-Blocks OBJECT-TYPE
	SYNTAX      Integer32
	MAX-ACCESS  read-only
	STATUS      current
	DESCRIPTION
		""
        ::= { exc2-Param-T2-PLP-B-Column-4 9 }

exc2-Param-T2-PLP-B-Column-4-Transmission-Mode OBJECT-TYPE
	SYNTAX      INTEGER {normal (0), highEfficiency (1)}
	MAX-ACCESS  read-only
	STATUS      current
	DESCRIPTION
		""
        ::= { exc2-Param-T2-PLP-B-Column-4 10 }

exc2-Param-T2-PLP-B-Column-4-ISSY OBJECT-TYPE
	SYNTAX      INTEGER {false(0), true(1)}
	MAX-ACCESS  read-only
	STATUS      current
	DESCRIPTION
		""
        ::= { exc2-Param-T2-PLP-B-Column-4 11 }

exc2-Param-T2-PLP-B-Column-4-NULL-Packet-Deletion OBJECT-TYPE
	SYNTAX      INTEGER {false(0), true(1)}
	MAX-ACCESS  read-only
	STATUS      current
	DESCRIPTION
		""
        ::= { exc2-Param-T2-PLP-B-Column-4 12 }

exc2-Param-T2-PLP-B-Column-4-In-Band-Signaling OBJECT-TYPE
	SYNTAX      INTEGER {false(0), true(1)}
	MAX-ACCESS  read-only
	STATUS      current
	DESCRIPTION
		""
        ::= { exc2-Param-T2-PLP-B-Column-4 13 }

exc2-Param-T2-PLP-B-Column-3-PLP-ID OBJECT-TYPE
	SYNTAX      Integer32
	MAX-ACCESS  read-only
	STATUS      current
	DESCRIPTION
		""
        ::= { exc2-Param-T2-PLP-B-Column-3 1 }

exc2-Param-T2-PLP-B-Column-3-PLP-Type OBJECT-TYPE
	SYNTAX      INTEGER {common (0), type1 (1), type2 (2)}
	MAX-ACCESS  read-only
	STATUS      current
	DESCRIPTION
		""
        ::= { exc2-Param-T2-PLP-B-Column-3 2 }

exc2-Param-T2-PLP-B-Column-3-LDPC OBJECT-TYPE
	SYNTAX      INTEGER {lDPC_16K (0), lDPC_64K (1)}
	MAX-ACCESS  read-only
	STATUS      current
	DESCRIPTION
		""
        ::= { exc2-Param-T2-PLP-B-Column-3 3 }

exc2-Param-T2-PLP-B-Column-3-Coderate OBJECT-TYPE
	SYNTAX      INTEGER {rate_1_2 (0), rate_3_5 (1), rate_2_3 (2), rate_3_4 (3), rate_4_5 (4), rate_5_6 (5)}
	MAX-ACCESS  read-only
	STATUS      current
	DESCRIPTION
		""
        ::= { exc2-Param-T2-PLP-B-Column-3 4 }

exc2-Param-T2-PLP-B-Column-3-Modulation OBJECT-TYPE
	SYNTAX      INTEGER {qPSK (0), qAM_16 (1), qAM_64 (2), qAM_256 (3)}
	MAX-ACCESS  read-only
	STATUS      current
	DESCRIPTION
		""
        ::= { exc2-Param-T2-PLP-B-Column-3 5 }

exc2-Param-T2-PLP-B-Column-3-Rotated-Constellation OBJECT-TYPE
	SYNTAX      INTEGER {notUsed (0), used (1)}
	MAX-ACCESS  read-only
	STATUS      current
	DESCRIPTION
		""
        ::= { exc2-Param-T2-PLP-B-Column-3 6 }

exc2-Param-T2-PLP-B-Column-3-Time-Interleave-Type OBJECT-TYPE
	SYNTAX      INTEGER {oneT2Frame (0), severalT2Frames (1), bypassed (2)}
	MAX-ACCESS  read-only
	STATUS      current
	DESCRIPTION
		""
        ::= { exc2-Param-T2-PLP-B-Column-3 7 }

exc2-Param-T2-PLP-B-Column-3-Time-Interleave-Length OBJECT-TYPE
	SYNTAX      Integer32
	MAX-ACCESS  read-only
	STATUS      current
	DESCRIPTION
		""
        ::= { exc2-Param-T2-PLP-B-Column-3 8 }

exc2-Param-T2-PLP-B-Column-3-Number-of-FEC-Blocks OBJECT-TYPE
	SYNTAX      Integer32
	MAX-ACCESS  read-only
	STATUS      current
	DESCRIPTION
		""
        ::= { exc2-Param-T2-PLP-B-Column-3 9 }

exc2-Param-T2-PLP-B-Column-3-Transmission-Mode OBJECT-TYPE
	SYNTAX      INTEGER {normal (0), highEfficiency (1)}
	MAX-ACCESS  read-only
	STATUS      current
	DESCRIPTION
		""
        ::= { exc2-Param-T2-PLP-B-Column-3 10 }

exc2-Param-T2-PLP-B-Column-3-ISSY OBJECT-TYPE
	SYNTAX      INTEGER {false(0), true(1)}
	MAX-ACCESS  read-only
	STATUS      current
	DESCRIPTION
		""
        ::= { exc2-Param-T2-PLP-B-Column-3 11 }

exc2-Param-T2-PLP-B-Column-3-NULL-Packet-Deletion OBJECT-TYPE
	SYNTAX      INTEGER {false(0), true(1)}
	MAX-ACCESS  read-only
	STATUS      current
	DESCRIPTION
		""
        ::= { exc2-Param-T2-PLP-B-Column-3 12 }

exc2-Param-T2-PLP-B-Column-3-In-Band-Signaling OBJECT-TYPE
	SYNTAX      INTEGER {false(0), true(1)}
	MAX-ACCESS  read-only
	STATUS      current
	DESCRIPTION
		""
        ::= { exc2-Param-T2-PLP-B-Column-3 13 }

exc2-Param-T2-PLP-B-Column-2-PLP-ID OBJECT-TYPE
	SYNTAX      Integer32
	MAX-ACCESS  read-only
	STATUS      current
	DESCRIPTION
		""
        ::= { exc2-Param-T2-PLP-B-Column-2 1 }

exc2-Param-T2-PLP-B-Column-2-PLP-Type OBJECT-TYPE
	SYNTAX      INTEGER {common (0), type1 (1), type2 (2)}
	MAX-ACCESS  read-only
	STATUS      current
	DESCRIPTION
		""
        ::= { exc2-Param-T2-PLP-B-Column-2 2 }

exc2-Param-T2-PLP-B-Column-2-LDPC OBJECT-TYPE
	SYNTAX      INTEGER {lDPC_16K (0), lDPC_64K (1)}
	MAX-ACCESS  read-only
	STATUS      current
	DESCRIPTION
		""
        ::= { exc2-Param-T2-PLP-B-Column-2 3 }

exc2-Param-T2-PLP-B-Column-2-Coderate OBJECT-TYPE
	SYNTAX      INTEGER {rate_1_2 (0), rate_3_5 (1), rate_2_3 (2), rate_3_4 (3), rate_4_5 (4), rate_5_6 (5)}
	MAX-ACCESS  read-only
	STATUS      current
	DESCRIPTION
		""
        ::= { exc2-Param-T2-PLP-B-Column-2 4 }

exc2-Param-T2-PLP-B-Column-2-Modulation OBJECT-TYPE
	SYNTAX      INTEGER {qPSK (0), qAM_16 (1), qAM_64 (2), qAM_256 (3)}
	MAX-ACCESS  read-only
	STATUS      current
	DESCRIPTION
		""
        ::= { exc2-Param-T2-PLP-B-Column-2 5 }

exc2-Param-T2-PLP-B-Column-2-Rotated-Constellation OBJECT-TYPE
	SYNTAX      INTEGER {notUsed (0), used (1)}
	MAX-ACCESS  read-only
	STATUS      current
	DESCRIPTION
		""
        ::= { exc2-Param-T2-PLP-B-Column-2 6 }

exc2-Param-T2-PLP-B-Column-2-Time-Interleave-Type OBJECT-TYPE
	SYNTAX      INTEGER {oneT2Frame (0), severalT2Frames (1), bypassed (2)}
	MAX-ACCESS  read-only
	STATUS      current
	DESCRIPTION
		""
        ::= { exc2-Param-T2-PLP-B-Column-2 7 }

exc2-Param-T2-PLP-B-Column-2-Time-Interleave-Length OBJECT-TYPE
	SYNTAX      Integer32
	MAX-ACCESS  read-only
	STATUS      current
	DESCRIPTION
		""
        ::= { exc2-Param-T2-PLP-B-Column-2 8 }

exc2-Param-T2-PLP-B-Column-2-Number-of-FEC-Blocks OBJECT-TYPE
	SYNTAX      Integer32
	MAX-ACCESS  read-only
	STATUS      current
	DESCRIPTION
		""
        ::= { exc2-Param-T2-PLP-B-Column-2 9 }

exc2-Param-T2-PLP-B-Column-2-Transmission-Mode OBJECT-TYPE
	SYNTAX      INTEGER {normal (0), highEfficiency (1)}
	MAX-ACCESS  read-only
	STATUS      current
	DESCRIPTION
		""
        ::= { exc2-Param-T2-PLP-B-Column-2 10 }

exc2-Param-T2-PLP-B-Column-2-ISSY OBJECT-TYPE
	SYNTAX      INTEGER {false(0), true(1)}
	MAX-ACCESS  read-only
	STATUS      current
	DESCRIPTION
		""
        ::= { exc2-Param-T2-PLP-B-Column-2 11 }

exc2-Param-T2-PLP-B-Column-2-NULL-Packet-Deletion OBJECT-TYPE
	SYNTAX      INTEGER {false(0), true(1)}
	MAX-ACCESS  read-only
	STATUS      current
	DESCRIPTION
		""
        ::= { exc2-Param-T2-PLP-B-Column-2 12 }

exc2-Param-T2-PLP-B-Column-2-In-Band-Signaling OBJECT-TYPE
	SYNTAX      INTEGER {false(0), true(1)}
	MAX-ACCESS  read-only
	STATUS      current
	DESCRIPTION
		""
        ::= { exc2-Param-T2-PLP-B-Column-2 13 }

exc2-Param-T2-PLP-B-Column-1-PLP-ID OBJECT-TYPE
	SYNTAX      Integer32
	MAX-ACCESS  read-only
	STATUS      current
	DESCRIPTION
		""
        ::= { exc2-Param-T2-PLP-B-Column-1 1 }

exc2-Param-T2-PLP-B-Column-1-PLP-Type OBJECT-TYPE
	SYNTAX      INTEGER {common (0), type1 (1), type2 (2)}
	MAX-ACCESS  read-only
	STATUS      current
	DESCRIPTION
		""
        ::= { exc2-Param-T2-PLP-B-Column-1 2 }

exc2-Param-T2-PLP-B-Column-1-LDPC OBJECT-TYPE
	SYNTAX      INTEGER {lDPC_16K (0), lDPC_64K (1)}
	MAX-ACCESS  read-only
	STATUS      current
	DESCRIPTION
		""
        ::= { exc2-Param-T2-PLP-B-Column-1 3 }

exc2-Param-T2-PLP-B-Column-1-Coderate OBJECT-TYPE
	SYNTAX      INTEGER {rate_1_2 (0), rate_3_5 (1), rate_2_3 (2), rate_3_4 (3), rate_4_5 (4), rate_5_6 (5)}
	MAX-ACCESS  read-only
	STATUS      current
	DESCRIPTION
		""
        ::= { exc2-Param-T2-PLP-B-Column-1 4 }

exc2-Param-T2-PLP-B-Column-1-Modulation OBJECT-TYPE
	SYNTAX      INTEGER {qPSK (0), qAM_16 (1), qAM_64 (2), qAM_256 (3)}
	MAX-ACCESS  read-only
	STATUS      current
	DESCRIPTION
		""
        ::= { exc2-Param-T2-PLP-B-Column-1 5 }

exc2-Param-T2-PLP-B-Column-1-Rotated-Constellation OBJECT-TYPE
	SYNTAX      INTEGER {notUsed (0), used (1)}
	MAX-ACCESS  read-only
	STATUS      current
	DESCRIPTION
		""
        ::= { exc2-Param-T2-PLP-B-Column-1 6 }

exc2-Param-T2-PLP-B-Column-1-Time-Interleave-Type OBJECT-TYPE
	SYNTAX      INTEGER {oneT2Frame (0), severalT2Frames (1), bypassed (2)}
	MAX-ACCESS  read-only
	STATUS      current
	DESCRIPTION
		""
        ::= { exc2-Param-T2-PLP-B-Column-1 7 }

exc2-Param-T2-PLP-B-Column-1-Time-Interleave-Length OBJECT-TYPE
	SYNTAX      Integer32
	MAX-ACCESS  read-only
	STATUS      current
	DESCRIPTION
		""
        ::= { exc2-Param-T2-PLP-B-Column-1 8 }

exc2-Param-T2-PLP-B-Column-1-Number-of-FEC-Blocks OBJECT-TYPE
	SYNTAX      Integer32
	MAX-ACCESS  read-only
	STATUS      current
	DESCRIPTION
		""
        ::= { exc2-Param-T2-PLP-B-Column-1 9 }

exc2-Param-T2-PLP-B-Column-1-Transmission-Mode OBJECT-TYPE
	SYNTAX      INTEGER {normal (0), highEfficiency (1)}
	MAX-ACCESS  read-only
	STATUS      current
	DESCRIPTION
		""
        ::= { exc2-Param-T2-PLP-B-Column-1 10 }

exc2-Param-T2-PLP-B-Column-1-ISSY OBJECT-TYPE
	SYNTAX      INTEGER {false(0), true(1)}
	MAX-ACCESS  read-only
	STATUS      current
	DESCRIPTION
		""
        ::= { exc2-Param-T2-PLP-B-Column-1 11 }

exc2-Param-T2-PLP-B-Column-1-NULL-Packet-Deletion OBJECT-TYPE
	SYNTAX      INTEGER {false(0), true(1)}
	MAX-ACCESS  read-only
	STATUS      current
	DESCRIPTION
		""
        ::= { exc2-Param-T2-PLP-B-Column-1 12 }

exc2-Param-T2-PLP-B-Column-1-In-Band-Signaling OBJECT-TYPE
	SYNTAX      INTEGER {false(0), true(1)}
	MAX-ACCESS  read-only
	STATUS      current
	DESCRIPTION
		""
        ::= { exc2-Param-T2-PLP-B-Column-1 13 }

exc2-Param-T2-PLP-A-PLP-ID OBJECT-TYPE
	SYNTAX      Integer32
	MAX-ACCESS  read-write
	STATUS      current
	DESCRIPTION
		""
        ::= { exc2-Param-T2-PLP-System-A 1 }

exc2-Param-T2-PLP-A-LDPC OBJECT-TYPE
	SYNTAX      INTEGER {lDPC_16K (0), lDPC_64K (1)}
	MAX-ACCESS  read-write
	STATUS      current
	DESCRIPTION
		""
        ::= { exc2-Param-T2-PLP-System-A 2 }

exc2-Param-T2-PLP-A-Coderate OBJECT-TYPE
	SYNTAX      INTEGER {rate_1_2 (0), rate_3_5 (1), rate_2_3 (2), rate_3_4 (3), rate_4_5 (4), rate_5_6 (5)}
	MAX-ACCESS  read-write
	STATUS      current
	DESCRIPTION
		""
        ::= { exc2-Param-T2-PLP-System-A 3 }

exc2-Param-T2-PLP-A-Modulation OBJECT-TYPE
	SYNTAX      INTEGER {qPSK (0), qAM_16 (1), qAM_64 (2), qAM_256 (3)}
	MAX-ACCESS  read-write
	STATUS      current
	DESCRIPTION
		""
        ::= { exc2-Param-T2-PLP-System-A 4 }

exc2-Param-T2-PLP-A-Rotated-Constellation OBJECT-TYPE
	SYNTAX      INTEGER {notUsed (0), used (1)}
	MAX-ACCESS  read-write
	STATUS      current
	DESCRIPTION
		""
        ::= { exc2-Param-T2-PLP-System-A 5 }

exc2-Param-T2-PLP-A-Time-Interleave-Type OBJECT-TYPE
	SYNTAX      INTEGER {oneT2Frame (0), severalT2Frames (1), bypassed (2)}
	MAX-ACCESS  read-write
	STATUS      current
	DESCRIPTION
		""
        ::= { exc2-Param-T2-PLP-System-A 6 }

exc2-Param-T2-PLP-A-Time-Interleave-Length OBJECT-TYPE
	SYNTAX      Integer32
	MAX-ACCESS  read-write
	STATUS      current
	DESCRIPTION
		""
        ::= { exc2-Param-T2-PLP-System-A 7 }

exc2-Param-T2-PLP-A-Number-of-FEC-Blocks OBJECT-TYPE
	SYNTAX      Integer32
	MAX-ACCESS  read-write
	STATUS      current
	DESCRIPTION
		""
        ::= { exc2-Param-T2-PLP-System-A 8 }

exc2-Param-T2-PLP-A-ISSY OBJECT-TYPE
	SYNTAX      INTEGER {false(0), true(1)}
	MAX-ACCESS  read-write
	STATUS      current
	DESCRIPTION
		""
        ::= { exc2-Param-T2-PLP-System-A 9 }

exc2-Param-T2-PLP-A-NULL-Packet-Deletion OBJECT-TYPE
	SYNTAX      INTEGER {false(0), true(1)}
	MAX-ACCESS  read-write
	STATUS      current
	DESCRIPTION
		""
        ::= { exc2-Param-T2-PLP-System-A 10 }

exc2-Param-T2-Settings-Network-System-ID OBJECT-TYPE
	SYNTAX      Integer32
	MAX-ACCESS  read-write
	STATUS      current
	DESCRIPTION
		""
        ::= { exc2-Param-T2-Settings-Network 1 }

exc2-Param-T2-Settings-Network-Network-ID OBJECT-TYPE
	SYNTAX      Integer32
	MAX-ACCESS  read-write
	STATUS      current
	DESCRIPTION
		""
        ::= { exc2-Param-T2-Settings-Network 2 }

exc2-Param-T2-Settings-Network-Cell-ID OBJECT-TYPE
	SYNTAX      Integer32
	MAX-ACCESS  read-write
	STATUS      current
	DESCRIPTION
		""
        ::= { exc2-Param-T2-Settings-Network 3 }

exc2-Param-T2-Settings-Network-Transmitter-ID OBJECT-TYPE
	SYNTAX      Integer32
	MAX-ACCESS  read-write
	STATUS      current
	DESCRIPTION
		""
        ::= { exc2-Param-T2-Settings-Network 4 }

exc2-Param-T2-Settings-Network-Cell-ID-Set-by-User OBJECT-TYPE
	SYNTAX      INTEGER {false(0), true(1)}
	MAX-ACCESS  read-write
	STATUS      current
	DESCRIPTION
		""
        ::= { exc2-Param-T2-Settings-Network 5 }

exc2-Param-T2-Settings-PAPR-Tone-Reservation OBJECT-TYPE
	SYNTAX      INTEGER {disabled (0), enabled (1)}
	MAX-ACCESS  read-write
	STATUS      current
	DESCRIPTION
		""
        ::= { exc2-Param-T2-Settings-PAPR 1 }

exc2-Param-T2-Settings-Structure-Number-of-T2-Frames OBJECT-TYPE
	SYNTAX      Integer32
	MAX-ACCESS  read-write
	STATUS      current
	DESCRIPTION
		""
        ::= { exc2-Param-T2-Settings-Frame-Structure 1 }

exc2-Param-T2-Settings-Structure-Number-of-OFDM-Symbols OBJECT-TYPE
	SYNTAX      Integer32
	MAX-ACCESS  read-write
	STATUS      current
	DESCRIPTION
		""
        ::= { exc2-Param-T2-Settings-Frame-Structure 2 }

exc2-Param-T2-Settings-Structure-Signaling-Constellation OBJECT-TYPE
	SYNTAX      INTEGER {bPSK (0), qPSK (1), qAM_16 (2), qAM_64 (3)}
	MAX-ACCESS  read-write
	STATUS      current
	DESCRIPTION
		""
        ::= { exc2-Param-T2-Settings-Frame-Structure 3 }

exc2-Param-T2-Settings-Structure-Standard-Version OBJECT-TYPE
	SYNTAX      INTEGER {version_1_1_1 (0), version_1_2_1 (1), version_1_3_1 (2)}
	MAX-ACCESS  read-only
	STATUS      current
	DESCRIPTION
		""
        ::= { exc2-Param-T2-Settings-Frame-Structure 4 }

exc2-Param-T2-Settings-Modulation-Bandwidth OBJECT-TYPE
	SYNTAX      INTEGER {band_1_7Mhz (0), band_5Mhz (1), band_6Mhz (2), band_7Mhz (3), band_8Mhz (4), band_10Mhz (5)}
	MAX-ACCESS  read-write
	STATUS      current
	DESCRIPTION
		""
        ::= { exc2-Param-T2-Settings-Frame-Modulation 1 }

exc2-Param-T2-Settings-Modulation-FFT-Size OBJECT-TYPE
	SYNTAX      INTEGER {fFT_2K (0), fFT_8K (1), fFT_4K (2), fFT_1K (3), fFT_16K (4), fFT_32K (5)}
	MAX-ACCESS  read-write
	STATUS      current
	DESCRIPTION
		""
        ::= { exc2-Param-T2-Settings-Frame-Modulation 2 }

exc2-Param-T2-Settings-Modulation-Bandwidth-Extension OBJECT-TYPE
	SYNTAX      INTEGER {notUsed (0), used (1)}
	MAX-ACCESS  read-write
	STATUS      current
	DESCRIPTION
		""
        ::= { exc2-Param-T2-Settings-Frame-Modulation 3 }

exc2-Param-T2-Settings-Modulation-Guard-Interval OBJECT-TYPE
	SYNTAX      INTEGER {interval_1_32 (0), interval_1_16 (1), interval_1_8 (2), interval_1_4 (3), interval_1_128 (4), interval_19_128 (5), interval_19_256 (6)}
	MAX-ACCESS  read-write
	STATUS      current
	DESCRIPTION
		""
        ::= { exc2-Param-T2-Settings-Frame-Modulation 4 }

exc2-Param-T2-Settings-Modulation-Pilot-Pattern OBJECT-TYPE
	SYNTAX      INTEGER {pP1 (0), pP2 (1), pP3 (2), pP4 (3), pP5 (4), pP6 (5), pP7 (6), pP8 (7)}
	MAX-ACCESS  read-write
	STATUS      current
	DESCRIPTION
		""
        ::= { exc2-Param-T2-Settings-Frame-Modulation 5 }

exc2-Param-T2-Input-PID-of-MPEG2-TS-Packet OBJECT-TYPE
	SYNTAX      Integer32
	MAX-ACCESS  read-write
	STATUS      current
	DESCRIPTION
		""
        ::= { exc2-Param-T2-InputStream 1 }

exc2-Param-T2-Input-Input-Type OBJECT-TYPE
	SYNTAX      INTEGER {singlePLP (0), multiPLP (1)}
	MAX-ACCESS  read-write
	STATUS      current
	DESCRIPTION
		""
        ::= { exc2-Param-T2-InputStream 2 }

exc2-Param-T2-Input-Transmission-Mode OBJECT-TYPE
	SYNTAX      INTEGER {normal (0), highEfficiency (1)}
	MAX-ACCESS  read-write
	STATUS      current
	DESCRIPTION
		""
        ::= { exc2-Param-T2-InputStream 3 }

exc2-Param-T2-SFN-SFN-Synchronization OBJECT-TYPE
	SYNTAX      INTEGER {off (0), on (1)}
	MAX-ACCESS  read-write
	STATUS      current
	DESCRIPTION
		""
        ::= { exc2-Param-T2-SFN 1 }

exc2-Param-T2-SFN-SFN-Local-Time-Offset OBJECT-TYPE
	SYNTAX      Integer32
	MAX-ACCESS  read-write
	STATUS      current
	DESCRIPTION
		""
        ::= { exc2-Param-T2-SFN 2 }

exc2-Param-T2-SFN-SFN-Extended-Time-Offset OBJECT-TYPE
	SYNTAX      Integer32
	MAX-ACCESS  read-write
	STATUS      current
	DESCRIPTION
		""
        ::= { exc2-Param-T2-SFN 3 }

exc2-Param-T2-SFN-Output-Mode OBJECT-TYPE
	SYNTAX      INTEGER {sISO (0), mISO (1)}
	MAX-ACCESS  read-write
	STATUS      current
	DESCRIPTION
		""
        ::= { exc2-Param-T2-SFN 4 }

exc2-Param-T2-SFN-MISO-Group OBJECT-TYPE
	SYNTAX      INTEGER {group_1 (0), group_2 (1)}
	MAX-ACCESS  read-write
	STATUS      current
	DESCRIPTION
		""
        ::= { exc2-Param-T2-SFN 5 }

exc2-Param-T2-SFN-MISO-Group-Set-by-User OBJECT-TYPE
	SYNTAX      INTEGER {false(0), true(1)}
	MAX-ACCESS  read-write
	STATUS      current
	DESCRIPTION
		""
        ::= { exc2-Param-T2-SFN 6 }

exc2-Param-T-MIP-Control-MIP-Control OBJECT-TYPE
	SYNTAX      INTEGER {notEnabled (0), mandatory (1), mandatoryOptional (2)}
	MAX-ACCESS  read-write
	STATUS      current
	DESCRIPTION
		""
        ::= { exc2-Param-T-MIP-Control 1 }

exc2-Param-T-MIP-Control-Transmitter-ID OBJECT-TYPE
	SYNTAX      Integer32
	MAX-ACCESS  read-write
	STATUS      current
	DESCRIPTION
		""
        ::= { exc2-Param-T-MIP-Control 2 }

exc2-Param-T-MIP-Control-Mute-on-MIP-Synchro-Warning OBJECT-TYPE
	SYNTAX      INTEGER {manual (0), auto (1)}
	MAX-ACCESS  read-write
	STATUS      current
	DESCRIPTION
		""
        ::= { exc2-Param-T-MIP-Control 3 }

exc2-Param-T-MIP-Control-Resync-on-MIP-Synchro-Error OBJECT-TYPE
	SYNTAX      INTEGER {manual (0), auto (1)}
	MAX-ACCESS  read-write
	STATUS      current
	DESCRIPTION
		""
        ::= { exc2-Param-T-MIP-Control 4 }

exc2-Param-T-MIP-Control-Mute-Timeout-before-Mute-Request OBJECT-TYPE
	SYNTAX      Integer32
	MAX-ACCESS  read-write
	STATUS      current
	DESCRIPTION
		""
        ::= { exc2-Param-T-MIP-Control 5 }

exc2-Param-T-MIP-Control-Unmute-Threshold-before-Unmute-Request OBJECT-TYPE
	SYNTAX      Integer32
	MAX-ACCESS  read-write
	STATUS      current
	DESCRIPTION
		""
        ::= { exc2-Param-T-MIP-Control 6 }

exc2-Param-T-MIP-Control-Restart-Timeout-before-Restart-Request OBJECT-TYPE
	SYNTAX      Integer32
	MAX-ACCESS  read-write
	STATUS      current
	DESCRIPTION
		""
        ::= { exc2-Param-T-MIP-Control 7 }

exc2-Param-T-Specific-Config-Mute-on-MIP-is-Missing OBJECT-TYPE
	SYNTAX      INTEGER {false(0), true(1)}
	MAX-ACCESS  read-write
	STATUS      current
	DESCRIPTION
		""
        ::= { exc2-Param-T-Specific-Config 1 }

exc2-Param-T-Specific-Config-Network-Delay-Error OBJECT-TYPE
	SYNTAX      INTEGER {false(0), true(1)}
	MAX-ACCESS  read-write
	STATUS      current
	DESCRIPTION
		""
        ::= { exc2-Param-T-Specific-Config 2 }

exc2-Param-T-TPS-CELL-ID OBJECT-TYPE
	SYNTAX      Integer32
	MAX-ACCESS  read-write
	STATUS      current
	DESCRIPTION
		""
        ::= { exc2-Param-T-TPS 1 }

exc2-Param-T-TPS-CELL-ID-Insertion OBJECT-TYPE
	SYNTAX      INTEGER {deactivated (0), activated (1)}
	MAX-ACCESS  read-write
	STATUS      current
	DESCRIPTION
		""
        ::= { exc2-Param-T-TPS 2 }

exc2-Param-T-TPS-DVB-H-Signaling OBJECT-TYPE
	SYNTAX      INTEGER {off (0), on (1)}
	MAX-ACCESS  read-write
	STATUS      current
	DESCRIPTION
		""
        ::= { exc2-Param-T-TPS 3 }

exc2-Param-T-TPS-Time-Slicing-on-HP OBJECT-TYPE
	SYNTAX      INTEGER {notUsed (0), used (1)}
	MAX-ACCESS  read-write
	STATUS      current
	DESCRIPTION
		""
        ::= { exc2-Param-T-TPS 4 }

exc2-Param-T-TPS-MPE-FEC-on-HP OBJECT-TYPE
	SYNTAX      INTEGER {notUsed (0), used (1)}
	MAX-ACCESS  read-write
	STATUS      current
	DESCRIPTION
		""
        ::= { exc2-Param-T-TPS 5 }

exc2-Param-T-TPS-Time-Slicing-on-LP OBJECT-TYPE
	SYNTAX      INTEGER {notUsed (0), used (1)}
	MAX-ACCESS  read-write
	STATUS      current
	DESCRIPTION
		""
        ::= { exc2-Param-T-TPS 6 }

exc2-Param-T-TPS-MPE-FEC-on-LP OBJECT-TYPE
	SYNTAX      INTEGER {notUsed (0), used (1)}
	MAX-ACCESS  read-write
	STATUS      current
	DESCRIPTION
		""
        ::= { exc2-Param-T-TPS 7 }

exc2-Param-T-TPS-Special-Bits OBJECT-TYPE
	SYNTAX      Integer32
	MAX-ACCESS  read-write
	STATUS      current
	DESCRIPTION
		""
        ::= { exc2-Param-T-TPS 8 }

exc2-Param-T-Mode-Bandwidth OBJECT-TYPE
	SYNTAX      INTEGER {band_5Mhz (0), band_6Mhz (1), band_7Mhz (2), band_8Mhz (3)}
	MAX-ACCESS  read-write
	STATUS      current
	DESCRIPTION
		""
        ::= { exc2-Param-T-Mode 1 }

exc2-Param-T-Mode-FFT-Mode OBJECT-TYPE
	SYNTAX      INTEGER {fFT_2K (0), fFT_8K (1), fFT_4K (2)}
	MAX-ACCESS  read-write
	STATUS      current
	DESCRIPTION
		""
        ::= { exc2-Param-T-Mode 2 }

exc2-Param-T-Mode-Guard-Interval OBJECT-TYPE
	SYNTAX      INTEGER {interval_1_32 (0), interval_1_16 (1), interval_1_8 (2), interval_1_4 (3)}
	MAX-ACCESS  read-write
	STATUS      current
	DESCRIPTION
		""
        ::= { exc2-Param-T-Mode 3 }

exc2-Param-T-Mode-Constellation OBJECT-TYPE
	SYNTAX      INTEGER {qPSK (0), qAM_16 (1), qAM_64 (2)}
	MAX-ACCESS  read-write
	STATUS      current
	DESCRIPTION
		""
        ::= { exc2-Param-T-Mode 4 }

exc2-Param-T-Mode-Inner-Interleaver OBJECT-TYPE
	SYNTAX      INTEGER {native (0), inDepth (1)}
	MAX-ACCESS  read-write
	STATUS      current
	DESCRIPTION
		""
        ::= { exc2-Param-T-Mode 5 }

exc2-Param-T-Mode-Modulation OBJECT-TYPE
	SYNTAX      INTEGER {nonHierarchical (0), hierarAlpha1 (1), hierarAlpha2 (2), hierarAlpha4 (3)}
	MAX-ACCESS  read-write
	STATUS      current
	DESCRIPTION
		""
        ::= { exc2-Param-T-Mode 6 }

exc2-Param-T-Mode-HP-Coderate OBJECT-TYPE
	SYNTAX      INTEGER {rate_1_2 (0), rate_2_3 (1), rate_3_4 (2), rate_5_6 (3), rate_7_8 (4)}
	MAX-ACCESS  read-write
	STATUS      current
	DESCRIPTION
		""
        ::= { exc2-Param-T-Mode 7 }

exc2-Param-T-Mode-LP-Coderate OBJECT-TYPE
	SYNTAX      INTEGER {rate_1_2 (0), rate_2_3 (1), rate_3_4 (2), rate_5_6 (3), rate_7_8 (4)}
	MAX-ACCESS  read-write
	STATUS      current
	DESCRIPTION
		""
        ::= { exc2-Param-T-Mode 8 }

exc2-Param-T-SFN-Synchronization OBJECT-TYPE
	SYNTAX      INTEGER {mFN (0), sFN (1)}
	MAX-ACCESS  read-write
	STATUS      current
	DESCRIPTION
		""
        ::= { exc2-Param-T-SFN 1 }

exc2-Param-T-SFN-Fine-Time-Offset OBJECT-TYPE
	SYNTAX      Integer32
	MAX-ACCESS  read-write
	STATUS      current
	DESCRIPTION
		""
        ::= { exc2-Param-T-SFN 2 }

exc2-Param-T-SFN-Static-Time-Offset OBJECT-TYPE
	SYNTAX      Integer32
	MAX-ACCESS  read-write
	STATUS      current
	DESCRIPTION
		""
        ::= { exc2-Param-T-SFN 3 }

exc2-Param-T-SFN-Resynchronize-SFN OBJECT-TYPE
	SYNTAX      INTEGER {false(0), true(1)}
	MAX-ACCESS  read-write
	STATUS      current
	DESCRIPTION
		""
        ::= { exc2-Param-T-SFN 4 }

exc2-Param-T-MFN-Bitrate-Adaptation OBJECT-TYPE
	SYNTAX      INTEGER {false(0), true(1)}
	MAX-ACCESS  read-write
	STATUS      current
	DESCRIPTION
		""
        ::= { exc2-Param-T-MFN 1 }

exc2-Param-T-MFN-NIT-Table-Update OBJECT-TYPE
	SYNTAX      INTEGER {false(0), true(1)}
	MAX-ACCESS  read-write
	STATUS      current
	DESCRIPTION
		""
        ::= { exc2-Param-T-MFN 2 }

exc2-Param-T-MFN-Frequency-in-NIT-Table OBJECT-TYPE
	SYNTAX      Integer32
	MAX-ACCESS  read-write
	STATUS      current
	DESCRIPTION
		""
        ::= { exc2-Param-T-MFN 3 }

exc2-Param-Output-Starting-Delay OBJECT-TYPE
	SYNTAX      Integer32
	MAX-ACCESS  read-write
	STATUS      current
	DESCRIPTION
		""
        ::= { exc2-Param-Output 1 }

exc2-Param-Output-Gain-Offset OBJECT-TYPE
	SYNTAX      Integer32
	MAX-ACCESS  read-write
	STATUS      current
	DESCRIPTION
		""
        ::= { exc2-Param-Output 2 }

exc2-Param-Output-Attenuation OBJECT-TYPE
	SYNTAX      Integer32
	MAX-ACCESS  read-write
	STATUS      current
	DESCRIPTION
		""
        ::= { exc2-Param-Output 3 }

exc2-Param-Output-Is-Mute OBJECT-TYPE
	SYNTAX      INTEGER {false(0), true(1)}
	MAX-ACCESS  read-write
	STATUS      current
	DESCRIPTION
		""
        ::= { exc2-Param-Output 4 }

exc2-Param-Output-Is-RF-Maintain-On-Input-Stream OBJECT-TYPE
	SYNTAX      INTEGER {false(0), true(1)}
	MAX-ACCESS  read-write
	STATUS      current
	DESCRIPTION
		""
        ::= { exc2-Param-Output 5 }

exc2-Param-Output-Crest-Factor-Required OBJECT-TYPE
	SYNTAX      Integer32
	MAX-ACCESS  read-write
	STATUS      current
	DESCRIPTION
		""
        ::= { exc2-Param-Output 6 }

exc2-Param-Output-Crest-Factor-Optimization OBJECT-TYPE
	SYNTAX      Integer32
	MAX-ACCESS  read-write
	STATUS      current
	DESCRIPTION
		""
        ::= { exc2-Param-Output 7 }

exc2-Param-Output-Protection-Clipping OBJECT-TYPE
	SYNTAX      Integer32
	MAX-ACCESS  read-write
	STATUS      current
	DESCRIPTION
		""
        ::= { exc2-Param-Output 8 }

exc2-Param-Output-Linear-Precorrection OBJECT-TYPE
	SYNTAX      INTEGER {bypassed (0), enabled (1)}
	MAX-ACCESS  read-write
	STATUS      current
	DESCRIPTION
		""
        ::= { exc2-Param-Output 9 }

exc2-Param-Output-Non-Linear-Precorrection OBJECT-TYPE
	SYNTAX      INTEGER {bypassed (0), enabled (1)}
	MAX-ACCESS  read-write
	STATUS      current
	DESCRIPTION
		""
        ::= { exc2-Param-Output 10 }

exc2-Param-Output-Mute-on-PLL-Unlocked OBJECT-TYPE
	SYNTAX      INTEGER {false(0), true(1)}
	MAX-ACCESS  read-write
	STATUS      current
	DESCRIPTION
		""
        ::= { exc2-Param-Output 11 }

exc2-Param-Output-TV-Channel OBJECT-TYPE
	SYNTAX      Integer32
	MAX-ACCESS  read-only
	STATUS      current
	DESCRIPTION
		""
        ::= { exc2-Param-Output 12 }

exc2-Param-Output-Is-RF-Maintain-On-PPS-Resync OBJECT-TYPE
	SYNTAX      INTEGER {false(0), true(1)}
	MAX-ACCESS  read-write
	STATUS      current
	DESCRIPTION
		""
        ::= { exc2-Param-Output 13 }

exc2-Param-Input-Clever-IP-Primary-Input OBJECT-TYPE
	SYNTAX      INTEGER {iP1 (0), iP2 (1)}
	MAX-ACCESS  read-write
	STATUS      current
	DESCRIPTION
		""
        ::= { exc2-Param-Input-Clever-Switch-IP-Parameters 1 }

exc2-Param-Input-Clever-IP-Clever-Switch-IP OBJECT-TYPE
	SYNTAX      INTEGER {false(0), true(1)}
	MAX-ACCESS  read-write
	STATUS      current
	DESCRIPTION
		""
        ::= { exc2-Param-Input-Clever-Switch-IP-Parameters 2 }

exc2-Param-Input-Clever-IP-Auto-Switch-Back OBJECT-TYPE
	SYNTAX      INTEGER {false(0), true(1)}
	MAX-ACCESS  read-write
	STATUS      current
	DESCRIPTION
		""
        ::= { exc2-Param-Input-Clever-Switch-IP-Parameters 3 }

exc2-Param-Input-Clever-IP-RTP-Packet-Timeout OBJECT-TYPE
	SYNTAX      Integer32
	MAX-ACCESS  read-write
	STATUS      current
	DESCRIPTION
		""
        ::= { exc2-Param-Input-Clever-Switch-IP-Parameters 4 }

exc2-Param-Input-Clever-IP-RTP-Valid-Packet-Time OBJECT-TYPE
	SYNTAX      Integer32
	MAX-ACCESS  read-write
	STATUS      current
	DESCRIPTION
		""
        ::= { exc2-Param-Input-Clever-Switch-IP-Parameters 5 }

exc2-Param-Input-IP-2-IGMP-Mode OBJECT-TYPE
	SYNTAX      INTEGER {exclude (0), include (1)}
	MAX-ACCESS  read-write
	STATUS      current
	DESCRIPTION
		""
        ::= { exc2-Param-Input-IP-2-IGMP 1 }

exc2-Param-Input-IP-1-IGMP-Mode OBJECT-TYPE
	SYNTAX      INTEGER {exclude (0), include (1)}
	MAX-ACCESS  read-write
	STATUS      current
	DESCRIPTION
		""
        ::= { exc2-Param-Input-IP-1-IGMP 1 }

exc2-Param-Input-IP-2-RX-Reception-Mode OBJECT-TYPE
	SYNTAX      INTEGER {unicast (0), multicast (1)}
	MAX-ACCESS  read-write
	STATUS      current
	DESCRIPTION
		""
        ::= { exc2-Param-Input-IP-2-RX 1 }

exc2-Param-Input-IP-2-RX-IGMP-Version OBJECT-TYPE
	SYNTAX      INTEGER {ver2 (0), ver3 (1)}
	MAX-ACCESS  read-write
	STATUS      current
	DESCRIPTION
		""
        ::= { exc2-Param-Input-IP-2-RX 2 }

exc2-Param-Input-IP-2-RX-UDP-Port OBJECT-TYPE
	SYNTAX      Integer32
	MAX-ACCESS  read-write
	STATUS      current
	DESCRIPTION
		""
        ::= { exc2-Param-Input-IP-2-RX 3 }

exc2-Param-Input-IP-2-RX-UDP-Reception-Timeout OBJECT-TYPE
	SYNTAX      Integer32
	MAX-ACCESS  read-write
	STATUS      current
	DESCRIPTION
		""
        ::= { exc2-Param-Input-IP-2-RX 4 }

exc2-Param-Input-IP-2-RX-Multicast-Group-Address OBJECT-TYPE
	SYNTAX      IPAddress
	MAX-ACCESS  read-write
	STATUS      current
	DESCRIPTION
		""
        ::= { exc2-Param-Input-IP-2-RX 5 }

exc2-Param-Input-IP-2-RX-Receiver-Latency OBJECT-TYPE
	SYNTAX      Integer32
	MAX-ACCESS  read-write
	STATUS      current
	DESCRIPTION
		""
        ::= { exc2-Param-Input-IP-2-RX 6 }

exc2-Param-Input-IP-1-RX-Reception-Mode OBJECT-TYPE
	SYNTAX      INTEGER {unicast (0), multicast (1)}
	MAX-ACCESS  read-write
	STATUS      current
	DESCRIPTION
		""
        ::= { exc2-Param-Input-IP-1-RX 1 }

exc2-Param-Input-IP-1-RX-IGMP-Version OBJECT-TYPE
	SYNTAX      INTEGER {ver2 (0), ver3 (1)}
	MAX-ACCESS  read-write
	STATUS      current
	DESCRIPTION
		""
        ::= { exc2-Param-Input-IP-1-RX 2 }

exc2-Param-Input-IP-1-RX-UDP-Port OBJECT-TYPE
	SYNTAX      Integer32
	MAX-ACCESS  read-write
	STATUS      current
	DESCRIPTION
		""
        ::= { exc2-Param-Input-IP-1-RX 3 }

exc2-Param-Input-IP-1-RX-UDP-Reception-Timeout OBJECT-TYPE
	SYNTAX      Integer32
	MAX-ACCESS  read-write
	STATUS      current
	DESCRIPTION
		""
        ::= { exc2-Param-Input-IP-1-RX 4 }

exc2-Param-Input-IP-1-RX-Multicast-Group-Address OBJECT-TYPE
	SYNTAX      IPAddress
	MAX-ACCESS  read-write
	STATUS      current
	DESCRIPTION
		""
        ::= { exc2-Param-Input-IP-1-RX 5 }

exc2-Param-Input-IP-1-RX-Receiver-Latency OBJECT-TYPE
	SYNTAX      Integer32
	MAX-ACCESS  read-write
	STATUS      current
	DESCRIPTION
		""
        ::= { exc2-Param-Input-IP-1-RX 6 }

exc2-Param-Input-IP-2-DHCP OBJECT-TYPE
	SYNTAX      INTEGER {manually (0), dHCP (1)}
	MAX-ACCESS  read-only
	STATUS      current
	DESCRIPTION
		""
        ::= { exc2-Param-Input-IP-2-Control 1 }

exc2-Param-Input-IP-2-IP-Address OBJECT-TYPE
	SYNTAX      IPAddress
	MAX-ACCESS  read-write
	STATUS      current
	DESCRIPTION
		""
        ::= { exc2-Param-Input-IP-2-Control 2 }

exc2-Param-Input-IP-2-Subnet-Mask OBJECT-TYPE
	SYNTAX      IPAddress
	MAX-ACCESS  read-write
	STATUS      current
	DESCRIPTION
		""
        ::= { exc2-Param-Input-IP-2-Control 3 }

exc2-Param-Input-IP-2-Gateway OBJECT-TYPE
	SYNTAX      IPAddress
	MAX-ACCESS  read-write
	STATUS      current
	DESCRIPTION
		""
        ::= { exc2-Param-Input-IP-2-Control 4 }

exc2-Param-Input-IP-2-VLAN-ID OBJECT-TYPE
	SYNTAX      Integer32
	MAX-ACCESS  read-write
	STATUS      current
	DESCRIPTION
		""
        ::= { exc2-Param-Input-IP-2-Control 5 }

exc2-Param-Input-IP-2-Validate-Parameters OBJECT-TYPE
	SYNTAX      INTEGER {false(0), true(1)}
	MAX-ACCESS  read-write
	STATUS      current
	DESCRIPTION
		""
        ::= { exc2-Param-Input-IP-2-Control 6 }

exc2-Param-Input-IP-1-DHCP OBJECT-TYPE
	SYNTAX      INTEGER {manually (0), dHCP (1)}
	MAX-ACCESS  read-write
	STATUS      current
	DESCRIPTION
		""
        ::= { exc2-Param-Input-IP-1-Control 1 }

exc2-Param-Input-IP-1-IP-Address OBJECT-TYPE
	SYNTAX      IPAddress
	MAX-ACCESS  read-write
	STATUS      current
	DESCRIPTION
		""
        ::= { exc2-Param-Input-IP-1-Control 2 }

exc2-Param-Input-IP-1-Subnet-Mask OBJECT-TYPE
	SYNTAX      IPAddress
	MAX-ACCESS  read-write
	STATUS      current
	DESCRIPTION
		""
        ::= { exc2-Param-Input-IP-1-Control 3 }

exc2-Param-Input-IP-1-Gateway OBJECT-TYPE
	SYNTAX      IPAddress
	MAX-ACCESS  read-write
	STATUS      current
	DESCRIPTION
		""
        ::= { exc2-Param-Input-IP-1-Control 4 }

exc2-Param-Input-IP-1-VLAN-ID OBJECT-TYPE
	SYNTAX      Integer32
	MAX-ACCESS  read-write
	STATUS      current
	DESCRIPTION
		""
        ::= { exc2-Param-Input-IP-1-Control 5 }

exc2-Param-Input-IP-1-Validate-Parameters OBJECT-TYPE
	SYNTAX      INTEGER {false(0), true(1)}
	MAX-ACCESS  read-write
	STATUS      current
	DESCRIPTION
		""
        ::= { exc2-Param-Input-IP-1-Control 6 }

exc2-Param-Input-Clever-Switching OBJECT-TYPE
	SYNTAX      INTEGER {off (0), on (1)}
	MAX-ACCESS  read-write
	STATUS      current
	DESCRIPTION
		""
        ::= { exc2-Param-Input-Clever-Parameters 1 }

exc2-Param-Input-Clever-Auto-Switch-Back OBJECT-TYPE
	SYNTAX      INTEGER {off (0), on (1)}
	MAX-ACCESS  read-write
	STATUS      current
	DESCRIPTION
		""
        ::= { exc2-Param-Input-Clever-Parameters 2 }

exc2-Param-Input-Clever-Error-Threshold-Value OBJECT-TYPE
	SYNTAX      Integer32
	MAX-ACCESS  read-write
	STATUS      current
	DESCRIPTION
		""
        ::= { exc2-Param-Input-Clever-Parameters 3 }

exc2-Param-Input-Clever-Valid-Threshold-Value OBJECT-TYPE
	SYNTAX      Integer32
	MAX-ACCESS  read-write
	STATUS      current
	DESCRIPTION
		""
        ::= { exc2-Param-Input-Clever-Parameters 4 }

exc2-Param-Input-Main-TS-Source-Input-1 OBJECT-TYPE
	SYNTAX      INTEGER {off (0), aSI1 (1), aSI2 (2), iP (3), activeStream (5)}
	MAX-ACCESS  read-write
	STATUS      current
	DESCRIPTION
		""
        ::= { exc2-Param-Input-Main 1 }

exc2-Param-Input-Main-TS-Source-Input-2 OBJECT-TYPE
	SYNTAX      INTEGER {off (0), aSI1 (1), aSI2 (2), iP (3), activeStream (5)}
	MAX-ACCESS  read-write
	STATUS      current
	DESCRIPTION
		""
        ::= { exc2-Param-Input-Main 2 }

exc2-Param-Glonass-GPS-Control-Timestamp OBJECT-TYPE
	SYNTAX      INTEGER {gPS (1), gLONASS (2), uTC (3), uTC_SU (4)}
	MAX-ACCESS  read-write
	STATUS      current
	DESCRIPTION
		""
        ::= { exc2-Param-Glonass-GPS-Control 1 }

exc2-Param-Glonass-GPS-Control-Navigation-System OBJECT-TYPE
	SYNTAX      INTEGER {gPS_GLONASS (0), gPS (1), gLONASS (2), gPS_GLONASS_SBAS (10), gPS_SBAS (11), gLONASS_SBAS (12)}
	MAX-ACCESS  read-write
	STATUS      current
	DESCRIPTION
		""
        ::= { exc2-Param-Glonass-GPS-Control 2 }

exc2-Param-Glonass-GPS-Control-PPS-Delay OBJECT-TYPE
	SYNTAX      Integer32
	MAX-ACCESS  read-write
	STATUS      current
	DESCRIPTION
		""
        ::= { exc2-Param-Glonass-GPS-Control 3 }

exc2-Param-Glonass-GPS-Control-Receiver-Mode OBJECT-TYPE
	SYNTAX      INTEGER {navi (0), fixedCoordinates (1), averageCoordinates (2)}
	MAX-ACCESS  read-write
	STATUS      current
	DESCRIPTION
		""
        ::= { exc2-Param-Glonass-GPS-Control 4 }

exc2-Param-Glonass-GPS-Control-Coordinates-Averaging-Time OBJECT-TYPE
	SYNTAX      Integer32
	MAX-ACCESS  read-write
	STATUS      current
	DESCRIPTION
		""
        ::= { exc2-Param-Glonass-GPS-Control 5 }

exc2-Param-Glonass-GPS-Control-Minimal-SNR OBJECT-TYPE
	SYNTAX      Integer32
	MAX-ACCESS  read-write
	STATUS      current
	DESCRIPTION
		""
        ::= { exc2-Param-Glonass-GPS-Control 6 }

exc2-Param-Glonass-GPS-Monitoring-Module-Status-Normal OBJECT-TYPE
	SYNTAX      INTEGER {false(0), true(1)}
	MAX-ACCESS  read-only
	STATUS      current
	DESCRIPTION
		""
        ::= { exc2-Param-Glonass-GPS-Monitoring 1 }

exc2-Param-Glonass-GPS-Monitoring-Antenna-Status OBJECT-TYPE
	SYNTAX      INTEGER {normal (0), shortCircuit (1), noConnection (2)}
	MAX-ACCESS  read-only
	STATUS      current
	DESCRIPTION
		""
        ::= { exc2-Param-Glonass-GPS-Monitoring 2 }

exc2-Param-Glonass-GPS-Monitoring-Satellites-Lock OBJECT-TYPE
	SYNTAX      INTEGER {false(0), true(1)}
	MAX-ACCESS  read-only
	STATUS      current
	DESCRIPTION
		""
        ::= { exc2-Param-Glonass-GPS-Monitoring 3 }

exc2-Param-Glonass-GPS-Monitoring-PLL-Lock OBJECT-TYPE
	SYNTAX      INTEGER {false(0), true(1)}
	MAX-ACCESS  read-only
	STATUS      current
	DESCRIPTION
		""
        ::= { exc2-Param-Glonass-GPS-Monitoring 4 }

exc2-Param-Glonass-GPS-Monitoring-Mode OBJECT-TYPE
	SYNTAX      INTEGER {mode2D (0), mode3D (1)}
	MAX-ACCESS  read-only
	STATUS      current
	DESCRIPTION
		""
        ::= { exc2-Param-Glonass-GPS-Monitoring 5 }

exc2-Param-Glonass-GPS-Monitoring-Satellites-Number-GPS OBJECT-TYPE
	SYNTAX      Integer32
	MAX-ACCESS  read-only
	STATUS      current
	DESCRIPTION
		""
        ::= { exc2-Param-Glonass-GPS-Monitoring 6 }

exc2-Param-Glonass-GPS-Monitoring-Satellites-Number-GLONASS OBJECT-TYPE
	SYNTAX      Integer32
	MAX-ACCESS  read-only
	STATUS      current
	DESCRIPTION
		""
        ::= { exc2-Param-Glonass-GPS-Monitoring 7 }

exc2-Param-Glonass-GPS-Monitoring-Current-Time OBJECT-TYPE
	SYNTAX      OCTET STRING
	MAX-ACCESS  read-only
	STATUS      current
	DESCRIPTION
		""
        ::= { exc2-Param-Glonass-GPS-Monitoring 8 }

exc2-Param-Glonass-GPS-Monitoring-Current-Date OBJECT-TYPE
	SYNTAX      OCTET STRING
	MAX-ACCESS  read-only
	STATUS      current
	DESCRIPTION
		""
        ::= { exc2-Param-Glonass-GPS-Monitoring 9 }

exc2-Param-Glonass-GPS-Monitoring-Longitude OBJECT-TYPE
	SYNTAX      OCTET STRING
	MAX-ACCESS  read-only
	STATUS      current
	DESCRIPTION
		""
        ::= { exc2-Param-Glonass-GPS-Monitoring 10 }

exc2-Param-Glonass-GPS-Monitoring-Latitude OBJECT-TYPE
	SYNTAX      OCTET STRING
	MAX-ACCESS  read-only
	STATUS      current
	DESCRIPTION
		""
        ::= { exc2-Param-Glonass-GPS-Monitoring 11 }

exc2-Param-Glonass-GPS-Monitoring-Firmware-Version-Controller OBJECT-TYPE
	SYNTAX      OCTET STRING
	MAX-ACCESS  read-only
	STATUS      current
	DESCRIPTION
		""
        ::= { exc2-Param-Glonass-GPS-Monitoring 12 }

exc2-Param-Glonass-GPS-Monitoring-Firmware-Version-NAVIS OBJECT-TYPE
	SYNTAX      OCTET STRING
	MAX-ACCESS  read-only
	STATUS      current
	DESCRIPTION
		""
        ::= { exc2-Param-Glonass-GPS-Monitoring 13 }

exc2-Param-Ref-Lost-of-Reference-Signal-Timeout-Enable OBJECT-TYPE
	SYNTAX      INTEGER {false(0), true(1)}
	MAX-ACCESS  read-write
	STATUS      current
	DESCRIPTION
		""
        ::= { exc2-Param-Reference 1 }

exc2-Param-Ref-Lost-of-Reference-Signal-Timeout OBJECT-TYPE
	SYNTAX      Integer32
	MAX-ACCESS  read-write
	STATUS      current
	DESCRIPTION
		""
        ::= { exc2-Param-Reference 2 }

exc2-Param-Ref-PPS-Auto-Resync OBJECT-TYPE
	SYNTAX      INTEGER {false(0), true(1)}
	MAX-ACCESS  read-write
	STATUS      current
	DESCRIPTION
		""
        ::= { exc2-Param-Reference 3 }

exc2-Param-Ref-Reference-Source OBJECT-TYPE
	SYNTAX      INTEGER {internal10Mhz (0), external10Mhz (1), pPS (2)}
	MAX-ACCESS  read-write
	STATUS      current
	DESCRIPTION
		""
        ::= { exc2-Param-Reference 4 }

exc2-Param-Ref-PPS-Edge OBJECT-TYPE
	SYNTAX      INTEGER {rising (0), falling (1)}
	MAX-ACCESS  read-write
	STATUS      current
	DESCRIPTION
		""
        ::= { exc2-Param-Reference 5 }

exc2-Param-Ref-PPS-Source OBJECT-TYPE
	SYNTAX      INTEGER {embeddedGPS (0), external (1)}
	MAX-ACCESS  read-write
	STATUS      current
	DESCRIPTION
		""
        ::= { exc2-Param-Reference 6 }

exc2-Param-Ref-Backup-Clock-Source OBJECT-TYPE
	SYNTAX      INTEGER {internal10Mhz (0), external10Mhz (1), external1PPS (2)}
	MAX-ACCESS  read-write
	STATUS      current
	DESCRIPTION
		""
        ::= { exc2-Param-Reference 7 }

exc2-Param-Ref-PPS-Input-Output OBJECT-TYPE
	SYNTAX      INTEGER {input (0), output (1)}
	MAX-ACCESS  read-write
	STATUS      current
	DESCRIPTION
		""
        ::= { exc2-Param-Reference 8 }

exc2-Param-Mon-Clever-IP-Primary-Input-Status OBJECT-TYPE
	SYNTAX      INTEGER {ok (0), warning (1), failed (2)}
	MAX-ACCESS  read-only
	STATUS      current
	DESCRIPTION
		""
        ::= { exc2-Param-Mon-Clever-Switch-IP-Status 1 }

exc2-Param-Mon-Clever-IP-Secondary-Input-Status OBJECT-TYPE
	SYNTAX      INTEGER {ok (0), failed (1)}
	MAX-ACCESS  read-only
	STATUS      current
	DESCRIPTION
		""
        ::= { exc2-Param-Mon-Clever-Switch-IP-Status 2 }

exc2-Param-Mon-Clever-IP-Active-Stream OBJECT-TYPE
	SYNTAX      INTEGER {primaryInput (0), secondaryInput (1)}
	MAX-ACCESS  read-only
	STATUS      current
	DESCRIPTION
		""
        ::= { exc2-Param-Mon-Clever-Switch-IP-Status 3 }

exc2-Param-Mon-Clever-IP-RTP-Packet-Loss-Time OBJECT-TYPE
	SYNTAX      Integer32
	MAX-ACCESS  read-only
	STATUS      current
	DESCRIPTION
		""
        ::= { exc2-Param-Mon-Clever-Switch-IP-Status 4 }

exc2-Param-Mon-Clever-IP-RTP-Valid-Packet-Time OBJECT-TYPE
	SYNTAX      Integer32
	MAX-ACCESS  read-only
	STATUS      current
	DESCRIPTION
		""
        ::= { exc2-Param-Mon-Clever-Switch-IP-Status 5 }

exc2-Param-Mon-IP-2-RX-UDP-Reception-Active OBJECT-TYPE
	SYNTAX      INTEGER {false(0), true(1)}
	MAX-ACCESS  read-only
	STATUS      current
	DESCRIPTION
		""
        ::= { exc2-Param-Mon-IP-IP-2-RX-Status 1 }

exc2-Param-Mon-IP-2-RX-RTP-Locked OBJECT-TYPE
	SYNTAX      INTEGER {false(0), true(1)}
	MAX-ACCESS  read-only
	STATUS      current
	DESCRIPTION
		""
        ::= { exc2-Param-Mon-IP-IP-2-RX-Status 2 }

exc2-Param-Mon-IP-2-RX-High-Input-Bitrate OBJECT-TYPE
	SYNTAX      INTEGER {false(0), true(1)}
	MAX-ACCESS  read-only
	STATUS      current
	DESCRIPTION
		""
        ::= { exc2-Param-Mon-IP-IP-2-RX-Status 3 }

exc2-Param-Mon-IP-2-RX-Low-Latency OBJECT-TYPE
	SYNTAX      INTEGER {false(0), true(1)}
	MAX-ACCESS  read-only
	STATUS      current
	DESCRIPTION
		""
        ::= { exc2-Param-Mon-IP-IP-2-RX-Status 4 }

exc2-Param-Mon-IP-2-RX-FEC-Mode OBJECT-TYPE
	SYNTAX      INTEGER {none (0), fec1D (1), fec2D (2)}
	MAX-ACCESS  read-only
	STATUS      current
	DESCRIPTION
		""
        ::= { exc2-Param-Mon-IP-IP-2-RX-Status 5 }

exc2-Param-Mon-IP-2-RX-FEC-Columns-Number OBJECT-TYPE
	SYNTAX      Integer32
	MAX-ACCESS  read-only
	STATUS      current
	DESCRIPTION
		""
        ::= { exc2-Param-Mon-IP-IP-2-RX-Status 6 }

exc2-Param-Mon-IP-2-RX-FEC-Rows-Number OBJECT-TYPE
	SYNTAX      Integer32
	MAX-ACCESS  read-only
	STATUS      current
	DESCRIPTION
		""
        ::= { exc2-Param-Mon-IP-IP-2-RX-Status 7 }

exc2-Param-Mon-IP-2-RX-PER-before-FEC OBJECT-TYPE
	SYNTAX      Integer32
	MAX-ACCESS  read-only
	STATUS      current
	DESCRIPTION
		""
        ::= { exc2-Param-Mon-IP-IP-2-RX-Status 8 }

exc2-Param-Mon-IP-2-RX-Corrected-Packet-Counter OBJECT-TYPE
	SYNTAX      Integer32
	MAX-ACCESS  read-only
	STATUS      current
	DESCRIPTION
		""
        ::= { exc2-Param-Mon-IP-IP-2-RX-Status 9 }

exc2-Param-Mon-IP-2-RX-Uncorrected-Packet-Counter OBJECT-TYPE
	SYNTAX      Integer32
	MAX-ACCESS  read-only
	STATUS      current
	DESCRIPTION
		""
        ::= { exc2-Param-Mon-IP-IP-2-RX-Status 10 }

exc2-Param-Mon-IP-2-RX-Estimated-Latency OBJECT-TYPE
	SYNTAX      Integer32
	MAX-ACCESS  read-only
	STATUS      current
	DESCRIPTION
		""
        ::= { exc2-Param-Mon-IP-IP-2-RX-Status 11 }

exc2-Param-Mon-IP-1-RX-UDP-Reception-Active OBJECT-TYPE
	SYNTAX      INTEGER {false(0), true(1)}
	MAX-ACCESS  read-only
	STATUS      current
	DESCRIPTION
		""
        ::= { exc2-Param-Mon-IP-IP-1-RX-Status 1 }

exc2-Param-Mon-IP-1-RX-RTP-Locked OBJECT-TYPE
	SYNTAX      INTEGER {false(0), true(1)}
	MAX-ACCESS  read-only
	STATUS      current
	DESCRIPTION
		""
        ::= { exc2-Param-Mon-IP-IP-1-RX-Status 2 }

exc2-Param-Mon-IP-1-RX-High-Input-Bitrate OBJECT-TYPE
	SYNTAX      INTEGER {false(0), true(1)}
	MAX-ACCESS  read-only
	STATUS      current
	DESCRIPTION
		""
        ::= { exc2-Param-Mon-IP-IP-1-RX-Status 3 }

exc2-Param-Mon-IP-1-RX-Low-Latency OBJECT-TYPE
	SYNTAX      INTEGER {false(0), true(1)}
	MAX-ACCESS  read-only
	STATUS      current
	DESCRIPTION
		""
        ::= { exc2-Param-Mon-IP-IP-1-RX-Status 4 }

exc2-Param-Mon-IP-1-RX-FEC-Mode OBJECT-TYPE
	SYNTAX      INTEGER {none (0), fec1D (1), fec2D (2)}
	MAX-ACCESS  read-only
	STATUS      current
	DESCRIPTION
		""
        ::= { exc2-Param-Mon-IP-IP-1-RX-Status 5 }

exc2-Param-Mon-IP-1-RX-FEC-Columns-Number OBJECT-TYPE
	SYNTAX      Integer32
	MAX-ACCESS  read-only
	STATUS      current
	DESCRIPTION
		""
        ::= { exc2-Param-Mon-IP-IP-1-RX-Status 6 }

exc2-Param-Mon-IP-1-RX-FEC-Rows-Number OBJECT-TYPE
	SYNTAX      Integer32
	MAX-ACCESS  read-only
	STATUS      current
	DESCRIPTION
		""
        ::= { exc2-Param-Mon-IP-IP-1-RX-Status 7 }

exc2-Param-Mon-IP-1-RX-PER-before-FEC OBJECT-TYPE
	SYNTAX      Integer32
	MAX-ACCESS  read-only
	STATUS      current
	DESCRIPTION
		""
        ::= { exc2-Param-Mon-IP-IP-1-RX-Status 8 }

exc2-Param-Mon-IP-1-RX-Corrected-Packet-Counter OBJECT-TYPE
	SYNTAX      Integer32
	MAX-ACCESS  read-only
	STATUS      current
	DESCRIPTION
		""
        ::= { exc2-Param-Mon-IP-IP-1-RX-Status 9 }

exc2-Param-Mon-IP-1-RX-Uncorrected-Packet-Counter OBJECT-TYPE
	SYNTAX      Integer32
	MAX-ACCESS  read-only
	STATUS      current
	DESCRIPTION
		""
        ::= { exc2-Param-Mon-IP-IP-1-RX-Status 10 }

exc2-Param-Mon-IP-1-RX-Estimated-Latency OBJECT-TYPE
	SYNTAX      Integer32
	MAX-ACCESS  read-only
	STATUS      current
	DESCRIPTION
		""
        ::= { exc2-Param-Mon-IP-IP-1-RX-Status 11 }

exc2-Param-Mon-IP-2-Link-Status OBJECT-TYPE
	SYNTAX      INTEGER {linkDown (0), eth10Full (1), eth10Half (2), eth100Full (3), eth100Half (4), eth1000Full (5), eth1000Half (6)}
	MAX-ACCESS  read-only
	STATUS      current
	DESCRIPTION
		""
        ::= { exc2-Param-Mon-IP-IP-2-Status 1 }

exc2-Param-Mon-IP-2-Received-Packet-Counter OBJECT-TYPE
	SYNTAX      Integer32
	MAX-ACCESS  read-only
	STATUS      current
	DESCRIPTION
		""
        ::= { exc2-Param-Mon-IP-IP-2-Status 2 }

exc2-Param-Mon-IP-2-Transmitted-Packet-Counter OBJECT-TYPE
	SYNTAX      Integer32
	MAX-ACCESS  read-only
	STATUS      current
	DESCRIPTION
		""
        ::= { exc2-Param-Mon-IP-IP-2-Status 3 }

exc2-Param-Mon-IP-2-Ethernet-CRC-Error-Counter OBJECT-TYPE
	SYNTAX      Integer32
	MAX-ACCESS  read-only
	STATUS      current
	DESCRIPTION
		""
        ::= { exc2-Param-Mon-IP-IP-2-Status 4 }

exc2-Param-Mon-IP-1-Link-Status OBJECT-TYPE
	SYNTAX      INTEGER {linkDown (0), eth10Full (1), eth10Half (2), eth100Full (3), eth100Half (4), eth1000Full (5), eth1000Half (6)}
	MAX-ACCESS  read-only
	STATUS      current
	DESCRIPTION
		""
        ::= { exc2-Param-Mon-IP-IP-1-Status 1 }

exc2-Param-Mon-IP-1-Received-Packet-Counter OBJECT-TYPE
	SYNTAX      Integer32
	MAX-ACCESS  read-only
	STATUS      current
	DESCRIPTION
		""
        ::= { exc2-Param-Mon-IP-IP-1-Status 2 }

exc2-Param-Mon-IP-1-Transmitted-Packet-Counter OBJECT-TYPE
	SYNTAX      Integer32
	MAX-ACCESS  read-only
	STATUS      current
	DESCRIPTION
		""
        ::= { exc2-Param-Mon-IP-IP-1-Status 3 }

exc2-Param-Mon-IP-1-Ethernet-CRC-Error-Counter OBJECT-TYPE
	SYNTAX      Integer32
	MAX-ACCESS  read-only
	STATUS      current
	DESCRIPTION
		""
        ::= { exc2-Param-Mon-IP-IP-1-Status 4 }

exc2-Param-Mon-IP-Input-Signal-Detected OBJECT-TYPE
	SYNTAX      INTEGER {false(0), true(1)}
	MAX-ACCESS  read-only
	STATUS      current
	DESCRIPTION
		""
        ::= { exc2-Param-Mon-IP-Input-Status 1 }

exc2-Param-Mon-IP-Input-Synchronization-Lost OBJECT-TYPE
	SYNTAX      INTEGER {false(0), true(1)}
	MAX-ACCESS  read-only
	STATUS      current
	DESCRIPTION
		""
        ::= { exc2-Param-Mon-IP-Input-Status 2 }

exc2-Param-Mon-IP-Input-ISK-Char-Error OBJECT-TYPE
	SYNTAX      INTEGER {false(0), true(1)}
	MAX-ACCESS  read-only
	STATUS      current
	DESCRIPTION
		""
        ::= { exc2-Param-Mon-IP-Input-Status 3 }

exc2-Param-Mon-IP-Input-MPEG-TS-Packet-Length OBJECT-TYPE
	SYNTAX      INTEGER {false(0), true(1)}
	MAX-ACCESS  read-only
	STATUS      current
	DESCRIPTION
		""
        ::= { exc2-Param-Mon-IP-Input-Status 4 }

exc2-Param-Mon-IP-Input-FEC-Detected OBJECT-TYPE
	SYNTAX      INTEGER {false(0), true(1)}
	MAX-ACCESS  read-only
	STATUS      current
	DESCRIPTION
		""
        ::= { exc2-Param-Mon-IP-Input-Status 5 }

exc2-Param-Mon-IP-Input-Total-Bitrate OBJECT-TYPE
	SYNTAX      Integer32
	MAX-ACCESS  read-only
	STATUS      current
	DESCRIPTION
		""
        ::= { exc2-Param-Mon-IP-Input-Status 6 }

exc2-Param-Mon-ASI-2-Signal-Detected OBJECT-TYPE
	SYNTAX      INTEGER {false(0), true(1)}
	MAX-ACCESS  read-only
	STATUS      current
	DESCRIPTION
		""
        ::= { exc2-Param-Mon-ASI-2-Status 1 }

exc2-Param-Mon-ASI-2-Synchronization-Lost OBJECT-TYPE
	SYNTAX      INTEGER {false(0), true(1)}
	MAX-ACCESS  read-only
	STATUS      current
	DESCRIPTION
		""
        ::= { exc2-Param-Mon-ASI-2-Status 2 }

exc2-Param-Mon-ASI-2-ISK-Char-Error OBJECT-TYPE
	SYNTAX      INTEGER {false(0), true(1)}
	MAX-ACCESS  read-only
	STATUS      current
	DESCRIPTION
		""
        ::= { exc2-Param-Mon-ASI-2-Status 3 }

exc2-Param-Mon-ASI-2-MPEG-TS-Packet-Length OBJECT-TYPE
	SYNTAX      INTEGER {false(0), true(1)}
	MAX-ACCESS  read-only
	STATUS      current
	DESCRIPTION
		""
        ::= { exc2-Param-Mon-ASI-2-Status 4 }

exc2-Param-Mon-ASI-2-FEC-Detected OBJECT-TYPE
	SYNTAX      INTEGER {false(0), true(1)}
	MAX-ACCESS  read-only
	STATUS      current
	DESCRIPTION
		""
        ::= { exc2-Param-Mon-ASI-2-Status 5 }

exc2-Param-Mon-ASI-2-Total-Bitrate OBJECT-TYPE
	SYNTAX      Integer32
	MAX-ACCESS  read-only
	STATUS      current
	DESCRIPTION
		""
        ::= { exc2-Param-Mon-ASI-2-Status 6 }

exc2-Param-Mon-ASI-1-Signal-Detected OBJECT-TYPE
	SYNTAX      INTEGER {false(0), true(1)}
	MAX-ACCESS  read-only
	STATUS      current
	DESCRIPTION
		""
        ::= { exc2-Param-Mon-ASI-1-Status 1 }

exc2-Param-Mon-ASI-1-Synchronization-Lost OBJECT-TYPE
	SYNTAX      INTEGER {false(0), true(1)}
	MAX-ACCESS  read-only
	STATUS      current
	DESCRIPTION
		""
        ::= { exc2-Param-Mon-ASI-1-Status 2 }

exc2-Param-Mon-ASI-1-ISK-Char-Error OBJECT-TYPE
	SYNTAX      INTEGER {false(0), true(1)}
	MAX-ACCESS  read-only
	STATUS      current
	DESCRIPTION
		""
        ::= { exc2-Param-Mon-ASI-1-Status 3 }

exc2-Param-Mon-ASI-1-MPEG-TS-Packet-Length OBJECT-TYPE
	SYNTAX      INTEGER {false(0), true(1)}
	MAX-ACCESS  read-only
	STATUS      current
	DESCRIPTION
		""
        ::= { exc2-Param-Mon-ASI-1-Status 4 }

exc2-Param-Mon-ASI-1-FEC-Detected OBJECT-TYPE
	SYNTAX      INTEGER {false(0), true(1)}
	MAX-ACCESS  read-only
	STATUS      current
	DESCRIPTION
		""
        ::= { exc2-Param-Mon-ASI-1-Status 5 }

exc2-Param-Mon-ASI-1-Total-Bitrate OBJECT-TYPE
	SYNTAX      Integer32
	MAX-ACCESS  read-only
	STATUS      current
	DESCRIPTION
		""
        ::= { exc2-Param-Mon-ASI-1-Status 6 }

exc2-Param-Mon-Clever-Input-1-Status OBJECT-TYPE
	SYNTAX      INTEGER {ok (0), fail (1)}
	MAX-ACCESS  read-only
	STATUS      current
	DESCRIPTION
		""
        ::= { exc2-Param-Mon-Clever-Status 1 }

exc2-Param-Mon-Clever-Error-Counter OBJECT-TYPE
	SYNTAX      Unsigned32
	MAX-ACCESS  read-only
	STATUS      current
	DESCRIPTION
		""
        ::= { exc2-Param-Mon-Clever-Status 2 }

exc2-Param-Mon-Clever-Valid-Counter OBJECT-TYPE
	SYNTAX      Unsigned32
	MAX-ACCESS  read-only
	STATUS      current
	DESCRIPTION
		""
        ::= { exc2-Param-Mon-Clever-Status 3 }

exc2-Param-Mon-Stream2-Network-Delay OBJECT-TYPE
	SYNTAX      Integer32
	MAX-ACCESS  read-only
	STATUS      current
	DESCRIPTION
		""
        ::= { exc2-Param-Mon-Stream2 1 }

exc2-Param-Mon-Stream2-Max-Network-Delay OBJECT-TYPE
	SYNTAX      Integer32
	MAX-ACCESS  read-only
	STATUS      current
	DESCRIPTION
		""
        ::= { exc2-Param-Mon-Stream2 2 }

exc2-Param-Mon-Stream2-Average-Total-Bitrate OBJECT-TYPE
	SYNTAX      Integer32
	MAX-ACCESS  read-only
	STATUS      current
	DESCRIPTION
		""
        ::= { exc2-Param-Mon-Stream2 3 }

exc2-Param-Mon-Stream2-Average-Useful-Bitrate OBJECT-TYPE
	SYNTAX      Integer32
	MAX-ACCESS  read-only
	STATUS      current
	DESCRIPTION
		""
        ::= { exc2-Param-Mon-Stream2 4 }

exc2-Param-Mon-Stream1-Network-Delay OBJECT-TYPE
	SYNTAX      Integer32
	MAX-ACCESS  read-only
	STATUS      current
	DESCRIPTION
		""
        ::= { exc2-Param-Mon-Stream1 1 }

exc2-Param-Mon-Stream1-Max-Network-Delay OBJECT-TYPE
	SYNTAX      Integer32
	MAX-ACCESS  read-only
	STATUS      current
	DESCRIPTION
		""
        ::= { exc2-Param-Mon-Stream1 2 }

exc2-Param-Mon-Stream1-Average-Total-Bitrate OBJECT-TYPE
	SYNTAX      Integer32
	MAX-ACCESS  read-only
	STATUS      current
	DESCRIPTION
		""
        ::= { exc2-Param-Mon-Stream1 3 }

exc2-Param-Mon-Stream1-Average-Useful-Bitrate OBJECT-TYPE
	SYNTAX      Integer32
	MAX-ACCESS  read-only
	STATUS      current
	DESCRIPTION
		""
        ::= { exc2-Param-Mon-Stream1 4 }

exc2-Param-Mon-Main-Exciter-Power-Output OBJECT-TYPE
	SYNTAX      Integer32
	MAX-ACCESS  read-only
	STATUS      current
	DESCRIPTION
		""
        ::= { exc2-Param-Mon-Main 1 }

exc2-Param-Mon-Main-Standard OBJECT-TYPE
	SYNTAX      INTEGER {dVBTH (0), dVBT2 (4)}
	MAX-ACCESS  read-only
	STATUS      current
	DESCRIPTION
		""
        ::= { exc2-Param-Mon-Main 2 }

exc2-Param-Mon-Main-Selected-Reference OBJECT-TYPE
	SYNTAX      INTEGER {internal (0), external10Mhz (1), external1PPS (2)}
	MAX-ACCESS  read-only
	STATUS      current
	DESCRIPTION
		""
        ::= { exc2-Param-Mon-Main 3 }

exc2-Param-Mon-Main-Mute-Source OBJECT-TYPE
	SYNTAX      INTEGER {muteOff (0), muteOnLicenseFail (1), muteOnInitInProgress (2), muteOnUserRequest (3), muteOnStartingDelay (4), muteOnTsStreamError (5), muteOnReferenceError (6), muteOnHardwareError (7), muteOnFirmwareUpgrade (8), muteOnWarmUp (9), muteOnSettingsErrors (255)}
	MAX-ACCESS  read-only
	STATUS      current
	DESCRIPTION
		""
        ::= { exc2-Param-Mon-Main 4 }

exc2-Param-Mon-Main-RF-Frequency OBJECT-TYPE
	SYNTAX      Integer32
	MAX-ACCESS  read-only
	STATUS      current
	DESCRIPTION
		""
        ::= { exc2-Param-Mon-Main 5 }

exc2-Param-Mon-Main-TV-Channel OBJECT-TYPE
	SYNTAX      Integer32
	MAX-ACCESS  read-only
	STATUS      current
	DESCRIPTION
		""
        ::= { exc2-Param-Mon-Main 6 }

exc2-Param-Mon-Main-Selected-Input OBJECT-TYPE
	SYNTAX      INTEGER {stream1 (0), stream2 (1)}
	MAX-ACCESS  read-only
	STATUS      current
	DESCRIPTION
		""
        ::= { exc2-Param-Mon-Main 7 }

exc2-Param-Mon-Main-Temperature OBJECT-TYPE
	SYNTAX      Integer32
	MAX-ACCESS  read-only
	STATUS      current
	DESCRIPTION
		""
        ::= { exc2-Param-Mon-Main 8 }

exc2-Param-Mon-Main-Average-Useful-Stream-Bitrate OBJECT-TYPE
	SYNTAX      Integer32
	MAX-ACCESS  read-only
	STATUS      current
	DESCRIPTION
		""
        ::= { exc2-Param-Mon-Main 9 }

exc2-Param-Mon-Main-Time-Margin-Stream-1 OBJECT-TYPE
	SYNTAX      Integer32
	MAX-ACCESS  read-only
	STATUS      current
	DESCRIPTION
		""
        ::= { exc2-Param-Mon-Main 10 }

exc2-Param-Mon-Main-Time-Margin-Stream-2 OBJECT-TYPE
	SYNTAX      Integer32
	MAX-ACCESS  read-only
	STATUS      current
	DESCRIPTION
		""
        ::= { exc2-Param-Mon-Main 11 }

exc2-DisplayMain-Status-Info OBJECT-TYPE
	SYNTAX      OCTET STRING
	MAX-ACCESS  read-only
	STATUS      current
	DESCRIPTION
		""
        ::= { exc2-Display-Main 1 }

exc2-DisplayMain-Status-Warning OBJECT-TYPE
	SYNTAX      OCTET STRING
	MAX-ACCESS  read-only
	STATUS      current
	DESCRIPTION
		""
        ::= { exc2-Display-Main 2 }

exc2-DisplayMain-Status-Failure OBJECT-TYPE
	SYNTAX      OCTET STRING
	MAX-ACCESS  read-only
	STATUS      current
	DESCRIPTION
		""
        ::= { exc2-Display-Main 3 }

exc2-Aux-Cmd-Is-Get-Exciter-Power-Out OBJECT-TYPE
	SYNTAX      INTEGER {false(0), true(1)}
	MAX-ACCESS  read-only
	STATUS      current
	DESCRIPTION
		""
        ::= { exc2-Aux-Commands 1 }

exc2-Aux-Cmd-Is-Get-DVB-T2-Time-Margin OBJECT-TYPE
	SYNTAX      INTEGER {false(0), true(1)}
	MAX-ACCESS  read-only
	STATUS      current
	DESCRIPTION
		""
        ::= { exc2-Aux-Commands 2 }

exc2-Aux-Cmd-Is-Set-IP-Network-Iface-Cfg-Opt OBJECT-TYPE
	SYNTAX      INTEGER {false(0), true(1)}
	MAX-ACCESS  read-only
	STATUS      current
	DESCRIPTION
		""
        ::= { exc2-Aux-Commands 3 }

exc2-Aux-Cmd-Is-Get-Navis-Firmware-Version OBJECT-TYPE
	SYNTAX      INTEGER {false(0), true(1)}
	MAX-ACCESS  read-only
	STATUS      current
	DESCRIPTION
		""
        ::= { exc2-Aux-Commands 4 }

exc2-Aux-Cmd-Is-Get-Minimal-SNR OBJECT-TYPE
	SYNTAX      INTEGER {false(0), true(1)}
	MAX-ACCESS  read-only
	STATUS      current
	DESCRIPTION
		""
        ::= { exc2-Aux-Commands 5 }

exc2-Aux-Opt-Is-TS-Over-IP OBJECT-TYPE
	SYNTAX      INTEGER {false(0), true(1)}
	MAX-ACCESS  read-only
	STATUS      current
	DESCRIPTION
		""
        ::= { exc2-Aux-Options 1 }

exc2-Aux-Opt-Is-GPS OBJECT-TYPE
	SYNTAX      INTEGER {false(0), true(1)}
	MAX-ACCESS  read-only
	STATUS      current
	DESCRIPTION
		""
        ::= { exc2-Aux-Options 2 }

exc2-Aux-Opt-Is-G4C OBJECT-TYPE
	SYNTAX      INTEGER {false(0), true(1)}
	MAX-ACCESS  read-only
	STATUS      current
	DESCRIPTION
		""
        ::= { exc2-Aux-Options 3 }

exc2-Aux-Opt-Is-New-FTP OBJECT-TYPE
	SYNTAX      INTEGER {false(0), true(1)}
	MAX-ACCESS  read-only
	STATUS      current
	DESCRIPTION
		""
        ::= { exc2-Aux-Options 4 }

exc2-Aux-Values-Correct-Pilot-Patterns OBJECT-TYPE
	SYNTAX      Integer32
	MAX-ACCESS  read-only
	STATUS      current
	DESCRIPTION
		""
        ::= { exc2-Aux-Values 1 }

exc2-Aux-Values-Correct-Guard-Intervals OBJECT-TYPE
	SYNTAX      Integer32
	MAX-ACCESS  read-only
	STATUS      current
	DESCRIPTION
		""
        ::= { exc2-Aux-Values 2 }

exc2-Aux-Process-Is-Standard-Changing OBJECT-TYPE
	SYNTAX      INTEGER {false(0), true(1)}
	MAX-ACCESS  read-only
	STATUS      current
	DESCRIPTION
		""
        ::= { exc2-Aux-Processing 1 }

exc2-Aux-Process-Is-MT2-Rebooting OBJECT-TYPE
	SYNTAX      INTEGER {false(0), true(1)}
	MAX-ACCESS  read-only
	STATUS      current
	DESCRIPTION
		""
        ::= { exc2-Aux-Processing 2 }

exc2-Aux-Process-Is-MT2-Firmware-Updating OBJECT-TYPE
	SYNTAX      INTEGER {false(0), true(1)}
	MAX-ACCESS  read-only
	STATUS      current
	DESCRIPTION
		""
        ::= { exc2-Aux-Processing 3 }

exc2-Aux-Process-Is-Controller-Rebooting OBJECT-TYPE
	SYNTAX      INTEGER {false(0), true(1)}
	MAX-ACCESS  read-only
	STATUS      current
	DESCRIPTION
		""
        ::= { exc2-Aux-Processing 4 }

exc2-Aux-Connected-Is-Connected-DVBT2-Module OBJECT-TYPE
	SYNTAX      INTEGER {false(0), true(1)}
	MAX-ACCESS  read-only
	STATUS      current
	DESCRIPTION
		""
        ::= { exc2-Aux-Connected 1 }

exc2-Aux-Connected-Is-Connected-Glonass-Module OBJECT-TYPE
	SYNTAX      INTEGER {false(0), true(1)}
	MAX-ACCESS  read-only
	STATUS      current
	DESCRIPTION
		""
        ::= { exc2-Aux-Connected 2 }

exc2-Unit-Connected OBJECT-TYPE
	SYNTAX      INTEGER {false(0), true(1)}
	MAX-ACCESS  read-only
	STATUS      current
	DESCRIPTION
		""
        ::= { exc2-Unit 1 }

exc2-Unit-Warning   OBJECT-TYPE
	SYNTAX      INTEGER {false(0), true(1)}
	MAX-ACCESS  read-only
	STATUS      current
	DESCRIPTION
		""
        ::= { exc2-Unit 2 }

exc2-Unit-Failure   OBJECT-TYPE
	SYNTAX      INTEGER {false(0), true(1)}
	MAX-ACCESS  read-only
	STATUS      current
	DESCRIPTION
		""
        ::= { exc2-Unit 3 }

exc2-Unit-Busy      OBJECT-TYPE
	SYNTAX      Integer32
	MAX-ACCESS  read-only
	STATUS      current
	DESCRIPTION
		""
        ::= { exc2-Unit 4 }

exc2-Unit-Model     OBJECT-TYPE
	SYNTAX      OCTET STRING
	MAX-ACCESS  read-only
	STATUS      current
	DESCRIPTION
		""
        ::= { exc2-Unit 5 }

exc2-Unit-Serial-Number OBJECT-TYPE
	SYNTAX      Integer32
	MAX-ACCESS  read-only
	STATUS      current
	DESCRIPTION
		""
        ::= { exc2-Unit 6 }

exc2-Unit-Firmware-Version OBJECT-TYPE
	SYNTAX      OCTET STRING
	MAX-ACCESS  read-only
	STATUS      current
	DESCRIPTION
		""
        ::= { exc2-Unit 7 }

exc2-Unit-Uptime    OBJECT-TYPE
	SYNTAX      DateAndTime
	MAX-ACCESS  read-only
	STATUS      current
	DESCRIPTION
		"<unused>"
        ::= { exc2-Unit 8 }

exc2-Unit-Post-Writes-Count OBJECT-TYPE
	SYNTAX      Integer32
	MAX-ACCESS  read-only
	STATUS      current
	DESCRIPTION
		"<unused>"
        ::= { exc2-Unit 9 }

exc2-Unit-IP-Address OBJECT-TYPE
	SYNTAX      IPAddress
	MAX-ACCESS  read-only
	STATUS      current
	DESCRIPTION
		""
        ::= { exc2-Unit 10 }

exc2-Unit-TCP-Port  OBJECT-TYPE
	SYNTAX      Integer32
	MAX-ACCESS  read-only
	STATUS      current
	DESCRIPTION
		""
        ::= { exc2-Unit 11 }

exc2-Unit-Adapter   OBJECT-TYPE
	SYNTAX      OCTET STRING
	MAX-ACCESS  read-only
	STATUS      current
	DESCRIPTION
		"<unused>"
        ::= { exc2-Unit 12 }

exc2-Unit-Reconnects OBJECT-TYPE
	SYNTAX      Integer32
	MAX-ACCESS  read-only
	STATUS      current
	DESCRIPTION
		""
        ::= { exc2-Unit 13 }

exc1-Unified-Is-Busy OBJECT-TYPE
	SYNTAX      INTEGER {false(0), true(1)}
	MAX-ACCESS  read-only
	STATUS      current
	DESCRIPTION
		""
        ::= { exc1-Unified 1 }

exc1-Unified-Is-Mute OBJECT-TYPE
	SYNTAX      INTEGER {false(0), true(1)}
	MAX-ACCESS  read-write
	STATUS      current
	DESCRIPTION
		""
        ::= { exc1-Unified 2 }

exc1-Messages-Settings-Errors OBJECT-TYPE
	SYNTAX      OCTET STRING
	MAX-ACCESS  read-only
	STATUS      current
	DESCRIPTION
		""
        ::= { exc1-Messages 1 }

exc1-Messages-Failures OBJECT-TYPE
	SYNTAX      OCTET STRING
	MAX-ACCESS  read-only
	STATUS      current
	DESCRIPTION
		""
        ::= { exc1-Messages 2 }

exc1-Messages-Warnings OBJECT-TYPE
	SYNTAX      OCTET STRING
	MAX-ACCESS  read-only
	STATUS      current
	DESCRIPTION
		""
        ::= { exc1-Messages 3 }

exc1-Messages-Information OBJECT-TYPE
	SYNTAX      OCTET STRING
	MAX-ACCESS  read-only
	STATUS      current
	DESCRIPTION
		""
        ::= { exc1-Messages 4 }

exc1-Param-Precorrection-Lin-Ctl-Enabled OBJECT-TYPE
	SYNTAX      INTEGER {false(0), true(1)}
	MAX-ACCESS  read-write
	STATUS      current
	DESCRIPTION
		""
        ::= { exc1-Param-Precorrection-Lin-Control 1 }

exc1-Param-Precorrection-Lin-Ctl-Adaptation-Process OBJECT-TYPE
	SYNTAX      INTEGER {disabled (0), dAP (1)}
	MAX-ACCESS  read-write
	STATUS      current
	DESCRIPTION
		""
        ::= { exc1-Param-Precorrection-Lin-Control 2 }

exc1-Param-Precorrection-Lin-Ctl-Adaptation-Timeout OBJECT-TYPE
	SYNTAX      Integer32
	MAX-ACCESS  read-write
	STATUS      current
	DESCRIPTION
		""
        ::= { exc1-Param-Precorrection-Lin-Control 3 }

exc1-Param-Precorrection-Lin-Ctl-Reset OBJECT-TYPE
	SYNTAX      Integer32
	MAX-ACCESS  read-write
	STATUS      current
	DESCRIPTION
		"Set value 1 to reset Linear precorrection. Other values are ignored."
        ::= { exc1-Param-Precorrection-Lin-Control 4 }

exc1-Param-Precorrection-Lin-Ctl-Start OBJECT-TYPE
	SYNTAX      Integer32
	MAX-ACCESS  read-write
	STATUS      current
	DESCRIPTION
		"Set value 1 to start Linear precorrection. Other values are ignored."
        ::= { exc1-Param-Precorrection-Lin-Control 5 }

exc1-Param-Precorrection-Lin-Ctl-Stop OBJECT-TYPE
	SYNTAX      Integer32
	MAX-ACCESS  read-write
	STATUS      current
	DESCRIPTION
		"Set value 1 to stop Linear precorrection. Other values are ignored."
        ::= { exc1-Param-Precorrection-Lin-Control 6 }

exc1-Param-Precorrection-Lin-Mon-Algorithm-Status OBJECT-TYPE
	SYNTAX      INTEGER {noStatus (0), active (1), stoppedByUser (2), stoppedByTimeout (4), stoppedByUnstable (8)}
	MAX-ACCESS  read-only
	STATUS      current
	DESCRIPTION
		""
        ::= { exc1-Param-Precorrection-Lin-Monitoring 1 }

exc1-Param-Precorrection-Lin-Mon-Is-AGC-Lock OBJECT-TYPE
	SYNTAX      INTEGER {false(0), true(1)}
	MAX-ACCESS  read-only
	STATUS      current
	DESCRIPTION
		""
        ::= { exc1-Param-Precorrection-Lin-Monitoring 2 }

exc1-Param-Precorrection-Lin-Mon-Is-Synchronization OBJECT-TYPE
	SYNTAX      INTEGER {false(0), true(1)}
	MAX-ACCESS  read-only
	STATUS      current
	DESCRIPTION
		""
        ::= { exc1-Param-Precorrection-Lin-Monitoring 3 }

exc1-Param-Precorrection-Lin-Mon-Is-Input-Power-Low OBJECT-TYPE
	SYNTAX      INTEGER {false(0), true(1)}
	MAX-ACCESS  read-only
	STATUS      current
	DESCRIPTION
		""
        ::= { exc1-Param-Precorrection-Lin-Monitoring 4 }

exc1-Param-Precorrection-Lin-Mon-Is-Input-Power-High OBJECT-TYPE
	SYNTAX      INTEGER {false(0), true(1)}
	MAX-ACCESS  read-only
	STATUS      current
	DESCRIPTION
		""
        ::= { exc1-Param-Precorrection-Lin-Monitoring 5 }

exc1-Param-Precorrection-Lin-Mon-Input-Level OBJECT-TYPE
	SYNTAX      Integer32
	MAX-ACCESS  read-only
	STATUS      current
	DESCRIPTION
		""
        ::= { exc1-Param-Precorrection-Lin-Monitoring 6 }

exc1-Param-Precorrection-Lin-Mon-Ripple-Value OBJECT-TYPE
	SYNTAX      Integer32
	MAX-ACCESS  read-only
	STATUS      current
	DESCRIPTION
		""
        ::= { exc1-Param-Precorrection-Lin-Monitoring 7 }

exc1-Param-Precorrection-Lin-Mon-Elapsed-Time-After-DAP OBJECT-TYPE
	SYNTAX      Integer32
	MAX-ACCESS  read-only
	STATUS      current
	DESCRIPTION
		""
        ::= { exc1-Param-Precorrection-Lin-Monitoring 8 }

exc1-Param-Precorrection-NonLin-Ctl-Enabled OBJECT-TYPE
	SYNTAX      INTEGER {false(0), true(1)}
	MAX-ACCESS  read-write
	STATUS      current
	DESCRIPTION
		""
        ::= { exc1-Param-Precorrection-NonLin-Control 1 }

exc1-Param-Precorrection-NonLin-Ctl-Adaptation-Process OBJECT-TYPE
	SYNTAX      INTEGER {disabled (0), singleMode (1), nA (2), continuousMode (3)}
	MAX-ACCESS  read-write
	STATUS      current
	DESCRIPTION
		""
        ::= { exc1-Param-Precorrection-NonLin-Control 2 }

exc1-Param-Precorrection-NonLin-Ctl-Adaptation-Timeout OBJECT-TYPE
	SYNTAX      Integer32
	MAX-ACCESS  read-write
	STATUS      current
	DESCRIPTION
		""
        ::= { exc1-Param-Precorrection-NonLin-Control 3 }

exc1-Param-Precorrection-NonLin-Ctl-DAP-Mode OBJECT-TYPE
	SYNTAX      INTEGER {standard_Basic (0), advanced_GAP (1)}
	MAX-ACCESS  read-write
	STATUS      current
	DESCRIPTION
		""
        ::= { exc1-Param-Precorrection-NonLin-Control 4 }

exc1-Param-Precorrection-NonLin-Ctl-Reset OBJECT-TYPE
	SYNTAX      Integer32
	MAX-ACCESS  read-write
	STATUS      current
	DESCRIPTION
		"Set value 1 to reset Non-Linear precorrection. Other values are ignored."
        ::= { exc1-Param-Precorrection-NonLin-Control 5 }

exc1-Param-Precorrection-NonLin-Ctl-Start OBJECT-TYPE
	SYNTAX      Integer32
	MAX-ACCESS  read-write
	STATUS      current
	DESCRIPTION
		"Set value 1 to start Non-Linear precorrection. Other values are ignored."
        ::= { exc1-Param-Precorrection-NonLin-Control 6 }

exc1-Param-Precorrection-NonLin-Ctl-Stop OBJECT-TYPE
	SYNTAX      Integer32
	MAX-ACCESS  read-write
	STATUS      current
	DESCRIPTION
		"Set value 1 to stop Non-Linear precorrection. Other values are ignored."
        ::= { exc1-Param-Precorrection-NonLin-Control 7 }

exc1-Param-Precorrection-NonLin-Mon-Algorithm-Status OBJECT-TYPE
	SYNTAX      INTEGER {noStatus (0), active (1), stoppedByUser (2), stoppedByTimeout (4), nA (8), stoppedByUnstable (16)}
	MAX-ACCESS  read-only
	STATUS      current
	DESCRIPTION
		""
        ::= { exc1-Param-Precorrection-NonLin-Monitoring 1 }

exc1-Param-Precorrection-NonLin-Mon-Is-AGC-Lock OBJECT-TYPE
	SYNTAX      INTEGER {false(0), true(1)}
	MAX-ACCESS  read-only
	STATUS      current
	DESCRIPTION
		""
        ::= { exc1-Param-Precorrection-NonLin-Monitoring 2 }

exc1-Param-Precorrection-NonLin-Mon-Is-Synchronization OBJECT-TYPE
	SYNTAX      INTEGER {false(0), true(1)}
	MAX-ACCESS  read-only
	STATUS      current
	DESCRIPTION
		""
        ::= { exc1-Param-Precorrection-NonLin-Monitoring 3 }

exc1-Param-Precorrection-NonLin-Mon-Is-Input-Power-Low OBJECT-TYPE
	SYNTAX      INTEGER {false(0), true(1)}
	MAX-ACCESS  read-only
	STATUS      current
	DESCRIPTION
		""
        ::= { exc1-Param-Precorrection-NonLin-Monitoring 4 }

exc1-Param-Precorrection-NonLin-Mon-Is-Input-Power-High OBJECT-TYPE
	SYNTAX      INTEGER {false(0), true(1)}
	MAX-ACCESS  read-only
	STATUS      current
	DESCRIPTION
		""
        ::= { exc1-Param-Precorrection-NonLin-Monitoring 5 }

exc1-Param-Precorrection-NonLin-Mon-Input-Level OBJECT-TYPE
	SYNTAX      Integer32
	MAX-ACCESS  read-only
	STATUS      current
	DESCRIPTION
		""
        ::= { exc1-Param-Precorrection-NonLin-Monitoring 6 }

exc1-Param-Precorrection-NonLin-Mon-Left-Shoulder OBJECT-TYPE
	SYNTAX      Integer32
	MAX-ACCESS  read-only
	STATUS      current
	DESCRIPTION
		""
        ::= { exc1-Param-Precorrection-NonLin-Monitoring 7 }

exc1-Param-Precorrection-NonLin-Mon-Right-Shoulder OBJECT-TYPE
	SYNTAX      Integer32
	MAX-ACCESS  read-only
	STATUS      current
	DESCRIPTION
		""
        ::= { exc1-Param-Precorrection-NonLin-Monitoring 8 }

exc1-Param-Precorrection-NonLin-Mon-Elapsed-Time-After-DAP OBJECT-TYPE
	SYNTAX      Integer32
	MAX-ACCESS  read-only
	STATUS      current
	DESCRIPTION
		""
        ::= { exc1-Param-Precorrection-NonLin-Monitoring 9 }

exc1-Param-Precorrection-NonLin-Mon-MER OBJECT-TYPE
	SYNTAX      Integer32
	MAX-ACCESS  read-only
	STATUS      current
	DESCRIPTION
		"-1 = N/A"
        ::= { exc1-Param-Precorrection-NonLin-Monitoring 10 }

exc1-Param-Precorrection-NonLin-Mon-Crest-Factor OBJECT-TYPE
	SYNTAX      Integer32
	MAX-ACCESS  read-only
	STATUS      current
	DESCRIPTION
		"-1 = N/A"
        ::= { exc1-Param-Precorrection-NonLin-Monitoring 11 }

exc1-Param-Firmware-Update-Progress OBJECT-TYPE
	SYNTAX      Integer32
	MAX-ACCESS  read-only
	STATUS      current
	DESCRIPTION
		""
        ::= { exc1-Param-Firmware 1 }

exc1-Param-Firmware-Switch OBJECT-TYPE
	SYNTAX      Integer32
	MAX-ACCESS  read-write
	STATUS      current
	DESCRIPTION
		"Set value 1 to activate new firmware and reboot DVB-T/T2 module. Other values are ignored."
        ::= { exc1-Param-Firmware 2 }

exc1-Param-Service-Control-Standard OBJECT-TYPE
	SYNTAX      INTEGER {dVBTH (0), dVBT2 (4)}
	MAX-ACCESS  read-write
	STATUS      current
	DESCRIPTION
		""
        ::= { exc1-Param-Service-Control 1 }

exc1-Param-Service-Control-Stream-1-Monitoring OBJECT-TYPE
	SYNTAX      INTEGER {false(0), true(1)}
	MAX-ACCESS  read-write
	STATUS      current
	DESCRIPTION
		""
        ::= { exc1-Param-Service-Control 2 }

exc1-Param-Service-Control-Stream-2-Monitoring OBJECT-TYPE
	SYNTAX      INTEGER {false(0), true(1)}
	MAX-ACCESS  read-write
	STATUS      current
	DESCRIPTION
		""
        ::= { exc1-Param-Service-Control 3 }

exc1-Param-Service-Control-Reboot-MT2 OBJECT-TYPE
	SYNTAX      Integer32
	MAX-ACCESS  read-write
	STATUS      current
	DESCRIPTION
		"Set value 1 to reboot DVB-T/T2 module. Other values are ignored."
        ::= { exc1-Param-Service-Control 4 }

exc1-Param-Service-Control-Reboot-Controller OBJECT-TYPE
	SYNTAX      Integer32
	MAX-ACCESS  read-write
	STATUS      current
	DESCRIPTION
		"Set value 2 to reboot controller. Other values are ignored."
        ::= { exc1-Param-Service-Control 5 }

exc1-Param-Service-Monitoring-DVB-T2-Support OBJECT-TYPE
	SYNTAX      INTEGER {false(0), true(1)}
	MAX-ACCESS  read-only
	STATUS      current
	DESCRIPTION
		""
        ::= { exc1-Param-Service-Monitoring 1 }

exc1-Param-Service-Monitoring-DVB-TH-Support OBJECT-TYPE
	SYNTAX      INTEGER {false(0), true(1)}
	MAX-ACCESS  read-only
	STATUS      current
	DESCRIPTION
		""
        ::= { exc1-Param-Service-Monitoring 2 }

exc1-Param-Service-Monitoring-Controller-Serial-Number OBJECT-TYPE
	SYNTAX      OCTET STRING
	MAX-ACCESS  read-only
	STATUS      current
	DESCRIPTION
		""
        ::= { exc1-Param-Service-Monitoring 3 }

exc1-Param-Service-Monitoring-Controller-Hardware-Version OBJECT-TYPE
	SYNTAX      OCTET STRING
	MAX-ACCESS  read-only
	STATUS      current
	DESCRIPTION
		""
        ::= { exc1-Param-Service-Monitoring 4 }

exc1-Param-Service-Monitoring-Controller-Software-Version OBJECT-TYPE
	SYNTAX      OCTET STRING
	MAX-ACCESS  read-only
	STATUS      current
	DESCRIPTION
		""
        ::= { exc1-Param-Service-Monitoring 5 }

exc1-Param-Service-Monitoring-MT2-Serial-Number OBJECT-TYPE
	SYNTAX      OCTET STRING
	MAX-ACCESS  read-only
	STATUS      current
	DESCRIPTION
		""
        ::= { exc1-Param-Service-Monitoring 6 }

exc1-Param-Service-Monitoring-MT2-Hardware-Version OBJECT-TYPE
	SYNTAX      OCTET STRING
	MAX-ACCESS  read-only
	STATUS      current
	DESCRIPTION
		""
        ::= { exc1-Param-Service-Monitoring 7 }

exc1-Param-Service-Monitoring-MT2-Software-Version OBJECT-TYPE
	SYNTAX      OCTET STRING
	MAX-ACCESS  read-only
	STATUS      current
	DESCRIPTION
		""
        ::= { exc1-Param-Service-Monitoring 8 }

exc1-Param-Service-Monitoring-MT2-Type OBJECT-TYPE
	SYNTAX      OCTET STRING
	MAX-ACCESS  read-only
	STATUS      current
	DESCRIPTION
		""
        ::= { exc1-Param-Service-Monitoring 9 }

exc1-Param-Tests-PRBS-23-bits OBJECT-TYPE
	SYNTAX      INTEGER {false(0), true(1)}
	MAX-ACCESS  read-write
	STATUS      current
	DESCRIPTION
		""
        ::= { exc1-Param-Tests 1 }

exc1-Param-Tests-Central-Carriers-251-Canceled OBJECT-TYPE
	SYNTAX      INTEGER {false(0), true(1)}
	MAX-ACCESS  read-write
	STATUS      current
	DESCRIPTION
		""
        ::= { exc1-Param-Tests 2 }

exc1-Param-T2-PLP-B-Number-of-PLPs OBJECT-TYPE
	SYNTAX      Integer32
	MAX-ACCESS  read-only
	STATUS      current
	DESCRIPTION
		""
        ::= { exc1-Param-T2-PLP-System-B 1 }

exc1-Param-T2-PLP-B-Column-16-PLP-ID OBJECT-TYPE
	SYNTAX      Integer32
	MAX-ACCESS  read-only
	STATUS      current
	DESCRIPTION
		""
        ::= { exc1-Param-T2-PLP-B-Column-16 1 }

exc1-Param-T2-PLP-B-Column-16-PLP-Type OBJECT-TYPE
	SYNTAX      INTEGER {common (0), type1 (1), type2 (2)}
	MAX-ACCESS  read-only
	STATUS      current
	DESCRIPTION
		""
        ::= { exc1-Param-T2-PLP-B-Column-16 2 }

exc1-Param-T2-PLP-B-Column-16-LDPC OBJECT-TYPE
	SYNTAX      INTEGER {lDPC_16K (0), lDPC_64K (1)}
	MAX-ACCESS  read-only
	STATUS      current
	DESCRIPTION
		""
        ::= { exc1-Param-T2-PLP-B-Column-16 3 }

exc1-Param-T2-PLP-B-Column-16-Coderate OBJECT-TYPE
	SYNTAX      INTEGER {rate_1_2 (0), rate_3_5 (1), rate_2_3 (2), rate_3_4 (3), rate_4_5 (4), rate_5_6 (5)}
	MAX-ACCESS  read-only
	STATUS      current
	DESCRIPTION
		""
        ::= { exc1-Param-T2-PLP-B-Column-16 4 }

exc1-Param-T2-PLP-B-Column-16-Modulation OBJECT-TYPE
	SYNTAX      INTEGER {qPSK (0), qAM_16 (1), qAM_64 (2), qAM_256 (3)}
	MAX-ACCESS  read-only
	STATUS      current
	DESCRIPTION
		""
        ::= { exc1-Param-T2-PLP-B-Column-16 5 }

exc1-Param-T2-PLP-B-Column-16-Rotated-Constellation OBJECT-TYPE
	SYNTAX      INTEGER {notUsed (0), used (1)}
	MAX-ACCESS  read-only
	STATUS      current
	DESCRIPTION
		""
        ::= { exc1-Param-T2-PLP-B-Column-16 6 }

exc1-Param-T2-PLP-B-Column-16-Time-Interleave-Type OBJECT-TYPE
	SYNTAX      INTEGER {oneT2Frame (0), severalT2Frames (1), bypassed (2)}
	MAX-ACCESS  read-only
	STATUS      current
	DESCRIPTION
		""
        ::= { exc1-Param-T2-PLP-B-Column-16 7 }

exc1-Param-T2-PLP-B-Column-16-Time-Interleave-Length OBJECT-TYPE
	SYNTAX      Integer32
	MAX-ACCESS  read-only
	STATUS      current
	DESCRIPTION
		""
        ::= { exc1-Param-T2-PLP-B-Column-16 8 }

exc1-Param-T2-PLP-B-Column-16-Number-of-FEC-Blocks OBJECT-TYPE
	SYNTAX      Integer32
	MAX-ACCESS  read-only
	STATUS      current
	DESCRIPTION
		""
        ::= { exc1-Param-T2-PLP-B-Column-16 9 }

exc1-Param-T2-PLP-B-Column-16-Transmission-Mode OBJECT-TYPE
	SYNTAX      INTEGER {normal (0), highEfficiency (1)}
	MAX-ACCESS  read-only
	STATUS      current
	DESCRIPTION
		""
        ::= { exc1-Param-T2-PLP-B-Column-16 10 }

exc1-Param-T2-PLP-B-Column-16-ISSY OBJECT-TYPE
	SYNTAX      INTEGER {false(0), true(1)}
	MAX-ACCESS  read-only
	STATUS      current
	DESCRIPTION
		""
        ::= { exc1-Param-T2-PLP-B-Column-16 11 }

exc1-Param-T2-PLP-B-Column-16-NULL-Packet-Deletion OBJECT-TYPE
	SYNTAX      INTEGER {false(0), true(1)}
	MAX-ACCESS  read-only
	STATUS      current
	DESCRIPTION
		""
        ::= { exc1-Param-T2-PLP-B-Column-16 12 }

exc1-Param-T2-PLP-B-Column-16-In-Band-Signaling OBJECT-TYPE
	SYNTAX      INTEGER {false(0), true(1)}
	MAX-ACCESS  read-only
	STATUS      current
	DESCRIPTION
		""
        ::= { exc1-Param-T2-PLP-B-Column-16 13 }

exc1-Param-T2-PLP-B-Column-15-PLP-ID OBJECT-TYPE
	SYNTAX      Integer32
	MAX-ACCESS  read-only
	STATUS      current
	DESCRIPTION
		""
        ::= { exc1-Param-T2-PLP-B-Column-15 1 }

exc1-Param-T2-PLP-B-Column-15-PLP-Type OBJECT-TYPE
	SYNTAX      INTEGER {common (0), type1 (1), type2 (2)}
	MAX-ACCESS  read-only
	STATUS      current
	DESCRIPTION
		""
        ::= { exc1-Param-T2-PLP-B-Column-15 2 }

exc1-Param-T2-PLP-B-Column-15-LDPC OBJECT-TYPE
	SYNTAX      INTEGER {lDPC_16K (0), lDPC_64K (1)}
	MAX-ACCESS  read-only
	STATUS      current
	DESCRIPTION
		""
        ::= { exc1-Param-T2-PLP-B-Column-15 3 }

exc1-Param-T2-PLP-B-Column-15-Coderate OBJECT-TYPE
	SYNTAX      INTEGER {rate_1_2 (0), rate_3_5 (1), rate_2_3 (2), rate_3_4 (3), rate_4_5 (4), rate_5_6 (5)}
	MAX-ACCESS  read-only
	STATUS      current
	DESCRIPTION
		""
        ::= { exc1-Param-T2-PLP-B-Column-15 4 }

exc1-Param-T2-PLP-B-Column-15-Modulation OBJECT-TYPE
	SYNTAX      INTEGER {qPSK (0), qAM_16 (1), qAM_64 (2), qAM_256 (3)}
	MAX-ACCESS  read-only
	STATUS      current
	DESCRIPTION
		""
        ::= { exc1-Param-T2-PLP-B-Column-15 5 }

exc1-Param-T2-PLP-B-Column-15-Rotated-Constellation OBJECT-TYPE
	SYNTAX      INTEGER {notUsed (0), used (1)}
	MAX-ACCESS  read-only
	STATUS      current
	DESCRIPTION
		""
        ::= { exc1-Param-T2-PLP-B-Column-15 6 }

exc1-Param-T2-PLP-B-Column-15-Time-Interleave-Type OBJECT-TYPE
	SYNTAX      INTEGER {oneT2Frame (0), severalT2Frames (1), bypassed (2)}
	MAX-ACCESS  read-only
	STATUS      current
	DESCRIPTION
		""
        ::= { exc1-Param-T2-PLP-B-Column-15 7 }

exc1-Param-T2-PLP-B-Column-15-Time-Interleave-Length OBJECT-TYPE
	SYNTAX      Integer32
	MAX-ACCESS  read-only
	STATUS      current
	DESCRIPTION
		""
        ::= { exc1-Param-T2-PLP-B-Column-15 8 }

exc1-Param-T2-PLP-B-Column-15-Number-of-FEC-Blocks OBJECT-TYPE
	SYNTAX      Integer32
	MAX-ACCESS  read-only
	STATUS      current
	DESCRIPTION
		""
        ::= { exc1-Param-T2-PLP-B-Column-15 9 }

exc1-Param-T2-PLP-B-Column-15-Transmission-Mode OBJECT-TYPE
	SYNTAX      INTEGER {normal (0), highEfficiency (1)}
	MAX-ACCESS  read-only
	STATUS      current
	DESCRIPTION
		""
        ::= { exc1-Param-T2-PLP-B-Column-15 10 }

exc1-Param-T2-PLP-B-Column-15-ISSY OBJECT-TYPE
	SYNTAX      INTEGER {false(0), true(1)}
	MAX-ACCESS  read-only
	STATUS      current
	DESCRIPTION
		""
        ::= { exc1-Param-T2-PLP-B-Column-15 11 }

exc1-Param-T2-PLP-B-Column-15-NULL-Packet-Deletion OBJECT-TYPE
	SYNTAX      INTEGER {false(0), true(1)}
	MAX-ACCESS  read-only
	STATUS      current
	DESCRIPTION
		""
        ::= { exc1-Param-T2-PLP-B-Column-15 12 }

exc1-Param-T2-PLP-B-Column-15-In-Band-Signaling OBJECT-TYPE
	SYNTAX      INTEGER {false(0), true(1)}
	MAX-ACCESS  read-only
	STATUS      current
	DESCRIPTION
		""
        ::= { exc1-Param-T2-PLP-B-Column-15 13 }

exc1-Param-T2-PLP-B-Column-14-PLP-ID OBJECT-TYPE
	SYNTAX      Integer32
	MAX-ACCESS  read-only
	STATUS      current
	DESCRIPTION
		""
        ::= { exc1-Param-T2-PLP-B-Column-14 1 }

exc1-Param-T2-PLP-B-Column-14-PLP-Type OBJECT-TYPE
	SYNTAX      INTEGER {common (0), type1 (1), type2 (2)}
	MAX-ACCESS  read-only
	STATUS      current
	DESCRIPTION
		""
        ::= { exc1-Param-T2-PLP-B-Column-14 2 }

exc1-Param-T2-PLP-B-Column-14-LDPC OBJECT-TYPE
	SYNTAX      INTEGER {lDPC_16K (0), lDPC_64K (1)}
	MAX-ACCESS  read-only
	STATUS      current
	DESCRIPTION
		""
        ::= { exc1-Param-T2-PLP-B-Column-14 3 }

exc1-Param-T2-PLP-B-Column-14-Coderate OBJECT-TYPE
	SYNTAX      INTEGER {rate_1_2 (0), rate_3_5 (1), rate_2_3 (2), rate_3_4 (3), rate_4_5 (4), rate_5_6 (5)}
	MAX-ACCESS  read-only
	STATUS      current
	DESCRIPTION
		""
        ::= { exc1-Param-T2-PLP-B-Column-14 4 }

exc1-Param-T2-PLP-B-Column-14-Modulation OBJECT-TYPE
	SYNTAX      INTEGER {qPSK (0), qAM_16 (1), qAM_64 (2), qAM_256 (3)}
	MAX-ACCESS  read-only
	STATUS      current
	DESCRIPTION
		""
        ::= { exc1-Param-T2-PLP-B-Column-14 5 }

exc1-Param-T2-PLP-B-Column-14-Rotated-Constellation OBJECT-TYPE
	SYNTAX      INTEGER {notUsed (0), used (1)}
	MAX-ACCESS  read-only
	STATUS      current
	DESCRIPTION
		""
        ::= { exc1-Param-T2-PLP-B-Column-14 6 }

exc1-Param-T2-PLP-B-Column-14-Time-Interleave-Type OBJECT-TYPE
	SYNTAX      INTEGER {oneT2Frame (0), severalT2Frames (1), bypassed (2)}
	MAX-ACCESS  read-only
	STATUS      current
	DESCRIPTION
		""
        ::= { exc1-Param-T2-PLP-B-Column-14 7 }

exc1-Param-T2-PLP-B-Column-14-Time-Interleave-Length OBJECT-TYPE
	SYNTAX      Integer32
	MAX-ACCESS  read-only
	STATUS      current
	DESCRIPTION
		""
        ::= { exc1-Param-T2-PLP-B-Column-14 8 }

exc1-Param-T2-PLP-B-Column-14-Number-of-FEC-Blocks OBJECT-TYPE
	SYNTAX      Integer32
	MAX-ACCESS  read-only
	STATUS      current
	DESCRIPTION
		""
        ::= { exc1-Param-T2-PLP-B-Column-14 9 }

exc1-Param-T2-PLP-B-Column-14-Transmission-Mode OBJECT-TYPE
	SYNTAX      INTEGER {normal (0), highEfficiency (1)}
	MAX-ACCESS  read-only
	STATUS      current
	DESCRIPTION
		""
        ::= { exc1-Param-T2-PLP-B-Column-14 10 }

exc1-Param-T2-PLP-B-Column-14-ISSY OBJECT-TYPE
	SYNTAX      INTEGER {false(0), true(1)}
	MAX-ACCESS  read-only
	STATUS      current
	DESCRIPTION
		""
        ::= { exc1-Param-T2-PLP-B-Column-14 11 }

exc1-Param-T2-PLP-B-Column-14-NULL-Packet-Deletion OBJECT-TYPE
	SYNTAX      INTEGER {false(0), true(1)}
	MAX-ACCESS  read-only
	STATUS      current
	DESCRIPTION
		""
        ::= { exc1-Param-T2-PLP-B-Column-14 12 }

exc1-Param-T2-PLP-B-Column-14-In-Band-Signaling OBJECT-TYPE
	SYNTAX      INTEGER {false(0), true(1)}
	MAX-ACCESS  read-only
	STATUS      current
	DESCRIPTION
		""
        ::= { exc1-Param-T2-PLP-B-Column-14 13 }

exc1-Param-T2-PLP-B-Column-13-PLP-ID OBJECT-TYPE
	SYNTAX      Integer32
	MAX-ACCESS  read-only
	STATUS      current
	DESCRIPTION
		""
        ::= { exc1-Param-T2-PLP-B-Column-13 1 }

exc1-Param-T2-PLP-B-Column-13-PLP-Type OBJECT-TYPE
	SYNTAX      INTEGER {common (0), type1 (1), type2 (2)}
	MAX-ACCESS  read-only
	STATUS      current
	DESCRIPTION
		""
        ::= { exc1-Param-T2-PLP-B-Column-13 2 }

exc1-Param-T2-PLP-B-Column-13-LDPC OBJECT-TYPE
	SYNTAX      INTEGER {lDPC_16K (0), lDPC_64K (1)}
	MAX-ACCESS  read-only
	STATUS      current
	DESCRIPTION
		""
        ::= { exc1-Param-T2-PLP-B-Column-13 3 }

exc1-Param-T2-PLP-B-Column-13-Coderate OBJECT-TYPE
	SYNTAX      INTEGER {rate_1_2 (0), rate_3_5 (1), rate_2_3 (2), rate_3_4 (3), rate_4_5 (4), rate_5_6 (5)}
	MAX-ACCESS  read-only
	STATUS      current
	DESCRIPTION
		""
        ::= { exc1-Param-T2-PLP-B-Column-13 4 }

exc1-Param-T2-PLP-B-Column-13-Modulation OBJECT-TYPE
	SYNTAX      INTEGER {qPSK (0), qAM_16 (1), qAM_64 (2), qAM_256 (3)}
	MAX-ACCESS  read-only
	STATUS      current
	DESCRIPTION
		""
        ::= { exc1-Param-T2-PLP-B-Column-13 5 }

exc1-Param-T2-PLP-B-Column-13-Rotated-Constellation OBJECT-TYPE
	SYNTAX      INTEGER {notUsed (0), used (1)}
	MAX-ACCESS  read-only
	STATUS      current
	DESCRIPTION
		""
        ::= { exc1-Param-T2-PLP-B-Column-13 6 }

exc1-Param-T2-PLP-B-Column-13-Time-Interleave-Type OBJECT-TYPE
	SYNTAX      INTEGER {oneT2Frame (0), severalT2Frames (1), bypassed (2)}
	MAX-ACCESS  read-only
	STATUS      current
	DESCRIPTION
		""
        ::= { exc1-Param-T2-PLP-B-Column-13 7 }

exc1-Param-T2-PLP-B-Column-13-Time-Interleave-Length OBJECT-TYPE
	SYNTAX      Integer32
	MAX-ACCESS  read-only
	STATUS      current
	DESCRIPTION
		""
        ::= { exc1-Param-T2-PLP-B-Column-13 8 }

exc1-Param-T2-PLP-B-Column-13-Number-of-FEC-Blocks OBJECT-TYPE
	SYNTAX      Integer32
	MAX-ACCESS  read-only
	STATUS      current
	DESCRIPTION
		""
        ::= { exc1-Param-T2-PLP-B-Column-13 9 }

exc1-Param-T2-PLP-B-Column-13-Transmission-Mode OBJECT-TYPE
	SYNTAX      INTEGER {normal (0), highEfficiency (1)}
	MAX-ACCESS  read-only
	STATUS      current
	DESCRIPTION
		""
        ::= { exc1-Param-T2-PLP-B-Column-13 10 }

exc1-Param-T2-PLP-B-Column-13-ISSY OBJECT-TYPE
	SYNTAX      INTEGER {false(0), true(1)}
	MAX-ACCESS  read-only
	STATUS      current
	DESCRIPTION
		""
        ::= { exc1-Param-T2-PLP-B-Column-13 11 }

exc1-Param-T2-PLP-B-Column-13-NULL-Packet-Deletion OBJECT-TYPE
	SYNTAX      INTEGER {false(0), true(1)}
	MAX-ACCESS  read-only
	STATUS      current
	DESCRIPTION
		""
        ::= { exc1-Param-T2-PLP-B-Column-13 12 }

exc1-Param-T2-PLP-B-Column-13-In-Band-Signaling OBJECT-TYPE
	SYNTAX      INTEGER {false(0), true(1)}
	MAX-ACCESS  read-only
	STATUS      current
	DESCRIPTION
		""
        ::= { exc1-Param-T2-PLP-B-Column-13 13 }

exc1-Param-T2-PLP-B-Column-12-PLP-ID OBJECT-TYPE
	SYNTAX      Integer32
	MAX-ACCESS  read-only
	STATUS      current
	DESCRIPTION
		""
        ::= { exc1-Param-T2-PLP-B-Column-12 1 }

exc1-Param-T2-PLP-B-Column-12-PLP-Type OBJECT-TYPE
	SYNTAX      INTEGER {common (0), type1 (1), type2 (2)}
	MAX-ACCESS  read-only
	STATUS      current
	DESCRIPTION
		""
        ::= { exc1-Param-T2-PLP-B-Column-12 2 }

exc1-Param-T2-PLP-B-Column-12-LDPC OBJECT-TYPE
	SYNTAX      INTEGER {lDPC_16K (0), lDPC_64K (1)}
	MAX-ACCESS  read-only
	STATUS      current
	DESCRIPTION
		""
        ::= { exc1-Param-T2-PLP-B-Column-12 3 }

exc1-Param-T2-PLP-B-Column-12-Coderate OBJECT-TYPE
	SYNTAX      INTEGER {rate_1_2 (0), rate_3_5 (1), rate_2_3 (2), rate_3_4 (3), rate_4_5 (4), rate_5_6 (5)}
	MAX-ACCESS  read-only
	STATUS      current
	DESCRIPTION
		""
        ::= { exc1-Param-T2-PLP-B-Column-12 4 }

exc1-Param-T2-PLP-B-Column-12-Modulation OBJECT-TYPE
	SYNTAX      INTEGER {qPSK (0), qAM_16 (1), qAM_64 (2), qAM_256 (3)}
	MAX-ACCESS  read-only
	STATUS      current
	DESCRIPTION
		""
        ::= { exc1-Param-T2-PLP-B-Column-12 5 }

exc1-Param-T2-PLP-B-Column-12-Rotated-Constellation OBJECT-TYPE
	SYNTAX      INTEGER {notUsed (0), used (1)}
	MAX-ACCESS  read-only
	STATUS      current
	DESCRIPTION
		""
        ::= { exc1-Param-T2-PLP-B-Column-12 6 }

exc1-Param-T2-PLP-B-Column-12-Time-Interleave-Type OBJECT-TYPE
	SYNTAX      INTEGER {oneT2Frame (0), severalT2Frames (1), bypassed (2)}
	MAX-ACCESS  read-only
	STATUS      current
	DESCRIPTION
		""
        ::= { exc1-Param-T2-PLP-B-Column-12 7 }

exc1-Param-T2-PLP-B-Column-12-Time-Interleave-Length OBJECT-TYPE
	SYNTAX      Integer32
	MAX-ACCESS  read-only
	STATUS      current
	DESCRIPTION
		""
        ::= { exc1-Param-T2-PLP-B-Column-12 8 }

exc1-Param-T2-PLP-B-Column-12-Number-of-FEC-Blocks OBJECT-TYPE
	SYNTAX      Integer32
	MAX-ACCESS  read-only
	STATUS      current
	DESCRIPTION
		""
        ::= { exc1-Param-T2-PLP-B-Column-12 9 }

exc1-Param-T2-PLP-B-Column-12-Transmission-Mode OBJECT-TYPE
	SYNTAX      INTEGER {normal (0), highEfficiency (1)}
	MAX-ACCESS  read-only
	STATUS      current
	DESCRIPTION
		""
        ::= { exc1-Param-T2-PLP-B-Column-12 10 }

exc1-Param-T2-PLP-B-Column-12-ISSY OBJECT-TYPE
	SYNTAX      INTEGER {false(0), true(1)}
	MAX-ACCESS  read-only
	STATUS      current
	DESCRIPTION
		""
        ::= { exc1-Param-T2-PLP-B-Column-12 11 }

exc1-Param-T2-PLP-B-Column-12-NULL-Packet-Deletion OBJECT-TYPE
	SYNTAX      INTEGER {false(0), true(1)}
	MAX-ACCESS  read-only
	STATUS      current
	DESCRIPTION
		""
        ::= { exc1-Param-T2-PLP-B-Column-12 12 }

exc1-Param-T2-PLP-B-Column-12-In-Band-Signaling OBJECT-TYPE
	SYNTAX      INTEGER {false(0), true(1)}
	MAX-ACCESS  read-only
	STATUS      current
	DESCRIPTION
		""
        ::= { exc1-Param-T2-PLP-B-Column-12 13 }

exc1-Param-T2-PLP-B-Column-11-PLP-ID OBJECT-TYPE
	SYNTAX      Integer32
	MAX-ACCESS  read-only
	STATUS      current
	DESCRIPTION
		""
        ::= { exc1-Param-T2-PLP-B-Column-11 1 }

exc1-Param-T2-PLP-B-Column-11-PLP-Type OBJECT-TYPE
	SYNTAX      INTEGER {common (0), type1 (1), type2 (2)}
	MAX-ACCESS  read-only
	STATUS      current
	DESCRIPTION
		""
        ::= { exc1-Param-T2-PLP-B-Column-11 2 }

exc1-Param-T2-PLP-B-Column-11-LDPC OBJECT-TYPE
	SYNTAX      INTEGER {lDPC_16K (0), lDPC_64K (1)}
	MAX-ACCESS  read-only
	STATUS      current
	DESCRIPTION
		""
        ::= { exc1-Param-T2-PLP-B-Column-11 3 }

exc1-Param-T2-PLP-B-Column-11-Coderate OBJECT-TYPE
	SYNTAX      INTEGER {rate_1_2 (0), rate_3_5 (1), rate_2_3 (2), rate_3_4 (3), rate_4_5 (4), rate_5_6 (5)}
	MAX-ACCESS  read-only
	STATUS      current
	DESCRIPTION
		""
        ::= { exc1-Param-T2-PLP-B-Column-11 4 }

exc1-Param-T2-PLP-B-Column-11-Modulation OBJECT-TYPE
	SYNTAX      INTEGER {qPSK (0), qAM_16 (1), qAM_64 (2), qAM_256 (3)}
	MAX-ACCESS  read-only
	STATUS      current
	DESCRIPTION
		""
        ::= { exc1-Param-T2-PLP-B-Column-11 5 }

exc1-Param-T2-PLP-B-Column-11-Rotated-Constellation OBJECT-TYPE
	SYNTAX      INTEGER {notUsed (0), used (1)}
	MAX-ACCESS  read-only
	STATUS      current
	DESCRIPTION
		""
        ::= { exc1-Param-T2-PLP-B-Column-11 6 }

exc1-Param-T2-PLP-B-Column-11-Time-Interleave-Type OBJECT-TYPE
	SYNTAX      INTEGER {oneT2Frame (0), severalT2Frames (1), bypassed (2)}
	MAX-ACCESS  read-only
	STATUS      current
	DESCRIPTION
		""
        ::= { exc1-Param-T2-PLP-B-Column-11 7 }

exc1-Param-T2-PLP-B-Column-11-Time-Interleave-Length OBJECT-TYPE
	SYNTAX      Integer32
	MAX-ACCESS  read-only
	STATUS      current
	DESCRIPTION
		""
        ::= { exc1-Param-T2-PLP-B-Column-11 8 }

exc1-Param-T2-PLP-B-Column-11-Number-of-FEC-Blocks OBJECT-TYPE
	SYNTAX      Integer32
	MAX-ACCESS  read-only
	STATUS      current
	DESCRIPTION
		""
        ::= { exc1-Param-T2-PLP-B-Column-11 9 }

exc1-Param-T2-PLP-B-Column-11-Transmission-Mode OBJECT-TYPE
	SYNTAX      INTEGER {normal (0), highEfficiency (1)}
	MAX-ACCESS  read-only
	STATUS      current
	DESCRIPTION
		""
        ::= { exc1-Param-T2-PLP-B-Column-11 10 }

exc1-Param-T2-PLP-B-Column-11-ISSY OBJECT-TYPE
	SYNTAX      INTEGER {false(0), true(1)}
	MAX-ACCESS  read-only
	STATUS      current
	DESCRIPTION
		""
        ::= { exc1-Param-T2-PLP-B-Column-11 11 }

exc1-Param-T2-PLP-B-Column-11-NULL-Packet-Deletion OBJECT-TYPE
	SYNTAX      INTEGER {false(0), true(1)}
	MAX-ACCESS  read-only
	STATUS      current
	DESCRIPTION
		""
        ::= { exc1-Param-T2-PLP-B-Column-11 12 }

exc1-Param-T2-PLP-B-Column-11-In-Band-Signaling OBJECT-TYPE
	SYNTAX      INTEGER {false(0), true(1)}
	MAX-ACCESS  read-only
	STATUS      current
	DESCRIPTION
		""
        ::= { exc1-Param-T2-PLP-B-Column-11 13 }

exc1-Param-T2-PLP-B-Column-10-PLP-ID OBJECT-TYPE
	SYNTAX      Integer32
	MAX-ACCESS  read-only
	STATUS      current
	DESCRIPTION
		""
        ::= { exc1-Param-T2-PLP-B-Column-10 1 }

exc1-Param-T2-PLP-B-Column-10-PLP-Type OBJECT-TYPE
	SYNTAX      INTEGER {common (0), type1 (1), type2 (2)}
	MAX-ACCESS  read-only
	STATUS      current
	DESCRIPTION
		""
        ::= { exc1-Param-T2-PLP-B-Column-10 2 }

exc1-Param-T2-PLP-B-Column-10-LDPC OBJECT-TYPE
	SYNTAX      INTEGER {lDPC_16K (0), lDPC_64K (1)}
	MAX-ACCESS  read-only
	STATUS      current
	DESCRIPTION
		""
        ::= { exc1-Param-T2-PLP-B-Column-10 3 }

exc1-Param-T2-PLP-B-Column-10-Coderate OBJECT-TYPE
	SYNTAX      INTEGER {rate_1_2 (0), rate_3_5 (1), rate_2_3 (2), rate_3_4 (3), rate_4_5 (4), rate_5_6 (5)}
	MAX-ACCESS  read-only
	STATUS      current
	DESCRIPTION
		""
        ::= { exc1-Param-T2-PLP-B-Column-10 4 }

exc1-Param-T2-PLP-B-Column-10-Modulation OBJECT-TYPE
	SYNTAX      INTEGER {qPSK (0), qAM_16 (1), qAM_64 (2), qAM_256 (3)}
	MAX-ACCESS  read-only
	STATUS      current
	DESCRIPTION
		""
        ::= { exc1-Param-T2-PLP-B-Column-10 5 }

exc1-Param-T2-PLP-B-Column-10-Rotated-Constellation OBJECT-TYPE
	SYNTAX      INTEGER {notUsed (0), used (1)}
	MAX-ACCESS  read-only
	STATUS      current
	DESCRIPTION
		""
        ::= { exc1-Param-T2-PLP-B-Column-10 6 }

exc1-Param-T2-PLP-B-Column-10-Time-Interleave-Type OBJECT-TYPE
	SYNTAX      INTEGER {oneT2Frame (0), severalT2Frames (1), bypassed (2)}
	MAX-ACCESS  read-only
	STATUS      current
	DESCRIPTION
		""
        ::= { exc1-Param-T2-PLP-B-Column-10 7 }

exc1-Param-T2-PLP-B-Column-10-Time-Interleave-Length OBJECT-TYPE
	SYNTAX      Integer32
	MAX-ACCESS  read-only
	STATUS      current
	DESCRIPTION
		""
        ::= { exc1-Param-T2-PLP-B-Column-10 8 }

exc1-Param-T2-PLP-B-Column-10-Number-of-FEC-Blocks OBJECT-TYPE
	SYNTAX      Integer32
	MAX-ACCESS  read-only
	STATUS      current
	DESCRIPTION
		""
        ::= { exc1-Param-T2-PLP-B-Column-10 9 }

exc1-Param-T2-PLP-B-Column-10-Transmission-Mode OBJECT-TYPE
	SYNTAX      INTEGER {normal (0), highEfficiency (1)}
	MAX-ACCESS  read-only
	STATUS      current
	DESCRIPTION
		""
        ::= { exc1-Param-T2-PLP-B-Column-10 10 }

exc1-Param-T2-PLP-B-Column-10-ISSY OBJECT-TYPE
	SYNTAX      INTEGER {false(0), true(1)}
	MAX-ACCESS  read-only
	STATUS      current
	DESCRIPTION
		""
        ::= { exc1-Param-T2-PLP-B-Column-10 11 }

exc1-Param-T2-PLP-B-Column-10-NULL-Packet-Deletion OBJECT-TYPE
	SYNTAX      INTEGER {false(0), true(1)}
	MAX-ACCESS  read-only
	STATUS      current
	DESCRIPTION
		""
        ::= { exc1-Param-T2-PLP-B-Column-10 12 }

exc1-Param-T2-PLP-B-Column-10-In-Band-Signaling OBJECT-TYPE
	SYNTAX      INTEGER {false(0), true(1)}
	MAX-ACCESS  read-only
	STATUS      current
	DESCRIPTION
		""
        ::= { exc1-Param-T2-PLP-B-Column-10 13 }

exc1-Param-T2-PLP-B-Column-9-PLP-ID OBJECT-TYPE
	SYNTAX      Integer32
	MAX-ACCESS  read-only
	STATUS      current
	DESCRIPTION
		""
        ::= { exc1-Param-T2-PLP-B-Column-9 1 }

exc1-Param-T2-PLP-B-Column-9-PLP-Type OBJECT-TYPE
	SYNTAX      INTEGER {common (0), type1 (1), type2 (2)}
	MAX-ACCESS  read-only
	STATUS      current
	DESCRIPTION
		""
        ::= { exc1-Param-T2-PLP-B-Column-9 2 }

exc1-Param-T2-PLP-B-Column-9-LDPC OBJECT-TYPE
	SYNTAX      INTEGER {lDPC_16K (0), lDPC_64K (1)}
	MAX-ACCESS  read-only
	STATUS      current
	DESCRIPTION
		""
        ::= { exc1-Param-T2-PLP-B-Column-9 3 }

exc1-Param-T2-PLP-B-Column-9-Coderate OBJECT-TYPE
	SYNTAX      INTEGER {rate_1_2 (0), rate_3_5 (1), rate_2_3 (2), rate_3_4 (3), rate_4_5 (4), rate_5_6 (5)}
	MAX-ACCESS  read-only
	STATUS      current
	DESCRIPTION
		""
        ::= { exc1-Param-T2-PLP-B-Column-9 4 }

exc1-Param-T2-PLP-B-Column-9-Modulation OBJECT-TYPE
	SYNTAX      INTEGER {qPSK (0), qAM_16 (1), qAM_64 (2), qAM_256 (3)}
	MAX-ACCESS  read-only
	STATUS      current
	DESCRIPTION
		""
        ::= { exc1-Param-T2-PLP-B-Column-9 5 }

exc1-Param-T2-PLP-B-Column-9-Rotated-Constellation OBJECT-TYPE
	SYNTAX      INTEGER {notUsed (0), used (1)}
	MAX-ACCESS  read-only
	STATUS      current
	DESCRIPTION
		""
        ::= { exc1-Param-T2-PLP-B-Column-9 6 }

exc1-Param-T2-PLP-B-Column-9-Time-Interleave-Type OBJECT-TYPE
	SYNTAX      INTEGER {oneT2Frame (0), severalT2Frames (1), bypassed (2)}
	MAX-ACCESS  read-only
	STATUS      current
	DESCRIPTION
		""
        ::= { exc1-Param-T2-PLP-B-Column-9 7 }

exc1-Param-T2-PLP-B-Column-9-Time-Interleave-Length OBJECT-TYPE
	SYNTAX      Integer32
	MAX-ACCESS  read-only
	STATUS      current
	DESCRIPTION
		""
        ::= { exc1-Param-T2-PLP-B-Column-9 8 }

exc1-Param-T2-PLP-B-Column-9-Number-of-FEC-Blocks OBJECT-TYPE
	SYNTAX      Integer32
	MAX-ACCESS  read-only
	STATUS      current
	DESCRIPTION
		""
        ::= { exc1-Param-T2-PLP-B-Column-9 9 }

exc1-Param-T2-PLP-B-Column-9-Transmission-Mode OBJECT-TYPE
	SYNTAX      INTEGER {normal (0), highEfficiency (1)}
	MAX-ACCESS  read-only
	STATUS      current
	DESCRIPTION
		""
        ::= { exc1-Param-T2-PLP-B-Column-9 10 }

exc1-Param-T2-PLP-B-Column-9-ISSY OBJECT-TYPE
	SYNTAX      INTEGER {false(0), true(1)}
	MAX-ACCESS  read-only
	STATUS      current
	DESCRIPTION
		""
        ::= { exc1-Param-T2-PLP-B-Column-9 11 }

exc1-Param-T2-PLP-B-Column-9-NULL-Packet-Deletion OBJECT-TYPE
	SYNTAX      INTEGER {false(0), true(1)}
	MAX-ACCESS  read-only
	STATUS      current
	DESCRIPTION
		""
        ::= { exc1-Param-T2-PLP-B-Column-9 12 }

exc1-Param-T2-PLP-B-Column-9-In-Band-Signaling OBJECT-TYPE
	SYNTAX      INTEGER {false(0), true(1)}
	MAX-ACCESS  read-only
	STATUS      current
	DESCRIPTION
		""
        ::= { exc1-Param-T2-PLP-B-Column-9 13 }

exc1-Param-T2-PLP-B-Column-8-PLP-ID OBJECT-TYPE
	SYNTAX      Integer32
	MAX-ACCESS  read-only
	STATUS      current
	DESCRIPTION
		""
        ::= { exc1-Param-T2-PLP-B-Column-8 1 }

exc1-Param-T2-PLP-B-Column-8-PLP-Type OBJECT-TYPE
	SYNTAX      INTEGER {common (0), type1 (1), type2 (2)}
	MAX-ACCESS  read-only
	STATUS      current
	DESCRIPTION
		""
        ::= { exc1-Param-T2-PLP-B-Column-8 2 }

exc1-Param-T2-PLP-B-Column-8-LDPC OBJECT-TYPE
	SYNTAX      INTEGER {lDPC_16K (0), lDPC_64K (1)}
	MAX-ACCESS  read-only
	STATUS      current
	DESCRIPTION
		""
        ::= { exc1-Param-T2-PLP-B-Column-8 3 }

exc1-Param-T2-PLP-B-Column-8-Coderate OBJECT-TYPE
	SYNTAX      INTEGER {rate_1_2 (0), rate_3_5 (1), rate_2_3 (2), rate_3_4 (3), rate_4_5 (4), rate_5_6 (5)}
	MAX-ACCESS  read-only
	STATUS      current
	DESCRIPTION
		""
        ::= { exc1-Param-T2-PLP-B-Column-8 4 }

exc1-Param-T2-PLP-B-Column-8-Modulation OBJECT-TYPE
	SYNTAX      INTEGER {qPSK (0), qAM_16 (1), qAM_64 (2), qAM_256 (3)}
	MAX-ACCESS  read-only
	STATUS      current
	DESCRIPTION
		""
        ::= { exc1-Param-T2-PLP-B-Column-8 5 }

exc1-Param-T2-PLP-B-Column-8-Rotated-Constellation OBJECT-TYPE
	SYNTAX      INTEGER {notUsed (0), used (1)}
	MAX-ACCESS  read-only
	STATUS      current
	DESCRIPTION
		""
        ::= { exc1-Param-T2-PLP-B-Column-8 6 }

exc1-Param-T2-PLP-B-Column-8-Time-Interleave-Type OBJECT-TYPE
	SYNTAX      INTEGER {oneT2Frame (0), severalT2Frames (1), bypassed (2)}
	MAX-ACCESS  read-only
	STATUS      current
	DESCRIPTION
		""
        ::= { exc1-Param-T2-PLP-B-Column-8 7 }

exc1-Param-T2-PLP-B-Column-8-Time-Interleave-Length OBJECT-TYPE
	SYNTAX      Integer32
	MAX-ACCESS  read-only
	STATUS      current
	DESCRIPTION
		""
        ::= { exc1-Param-T2-PLP-B-Column-8 8 }

exc1-Param-T2-PLP-B-Column-8-Number-of-FEC-Blocks OBJECT-TYPE
	SYNTAX      Integer32
	MAX-ACCESS  read-only
	STATUS      current
	DESCRIPTION
		""
        ::= { exc1-Param-T2-PLP-B-Column-8 9 }

exc1-Param-T2-PLP-B-Column-8-Transmission-Mode OBJECT-TYPE
	SYNTAX      INTEGER {normal (0), highEfficiency (1)}
	MAX-ACCESS  read-only
	STATUS      current
	DESCRIPTION
		""
        ::= { exc1-Param-T2-PLP-B-Column-8 10 }

exc1-Param-T2-PLP-B-Column-8-ISSY OBJECT-TYPE
	SYNTAX      INTEGER {false(0), true(1)}
	MAX-ACCESS  read-only
	STATUS      current
	DESCRIPTION
		""
        ::= { exc1-Param-T2-PLP-B-Column-8 11 }

exc1-Param-T2-PLP-B-Column-8-NULL-Packet-Deletion OBJECT-TYPE
	SYNTAX      INTEGER {false(0), true(1)}
	MAX-ACCESS  read-only
	STATUS      current
	DESCRIPTION
		""
        ::= { exc1-Param-T2-PLP-B-Column-8 12 }

exc1-Param-T2-PLP-B-Column-8-In-Band-Signaling OBJECT-TYPE
	SYNTAX      INTEGER {false(0), true(1)}
	MAX-ACCESS  read-only
	STATUS      current
	DESCRIPTION
		""
        ::= { exc1-Param-T2-PLP-B-Column-8 13 }

exc1-Param-T2-PLP-B-Column-7-PLP-ID OBJECT-TYPE
	SYNTAX      Integer32
	MAX-ACCESS  read-only
	STATUS      current
	DESCRIPTION
		""
        ::= { exc1-Param-T2-PLP-B-Column-7 1 }

exc1-Param-T2-PLP-B-Column-7-PLP-Type OBJECT-TYPE
	SYNTAX      INTEGER {common (0), type1 (1), type2 (2)}
	MAX-ACCESS  read-only
	STATUS      current
	DESCRIPTION
		""
        ::= { exc1-Param-T2-PLP-B-Column-7 2 }

exc1-Param-T2-PLP-B-Column-7-LDPC OBJECT-TYPE
	SYNTAX      INTEGER {lDPC_16K (0), lDPC_64K (1)}
	MAX-ACCESS  read-only
	STATUS      current
	DESCRIPTION
		""
        ::= { exc1-Param-T2-PLP-B-Column-7 3 }

exc1-Param-T2-PLP-B-Column-7-Coderate OBJECT-TYPE
	SYNTAX      INTEGER {rate_1_2 (0), rate_3_5 (1), rate_2_3 (2), rate_3_4 (3), rate_4_5 (4), rate_5_6 (5)}
	MAX-ACCESS  read-only
	STATUS      current
	DESCRIPTION
		""
        ::= { exc1-Param-T2-PLP-B-Column-7 4 }

exc1-Param-T2-PLP-B-Column-7-Modulation OBJECT-TYPE
	SYNTAX      INTEGER {qPSK (0), qAM_16 (1), qAM_64 (2), qAM_256 (3)}
	MAX-ACCESS  read-only
	STATUS      current
	DESCRIPTION
		""
        ::= { exc1-Param-T2-PLP-B-Column-7 5 }

exc1-Param-T2-PLP-B-Column-7-Rotated-Constellation OBJECT-TYPE
	SYNTAX      INTEGER {notUsed (0), used (1)}
	MAX-ACCESS  read-only
	STATUS      current
	DESCRIPTION
		""
        ::= { exc1-Param-T2-PLP-B-Column-7 6 }

exc1-Param-T2-PLP-B-Column-7-Time-Interleave-Type OBJECT-TYPE
	SYNTAX      INTEGER {oneT2Frame (0), severalT2Frames (1), bypassed (2)}
	MAX-ACCESS  read-only
	STATUS      current
	DESCRIPTION
		""
        ::= { exc1-Param-T2-PLP-B-Column-7 7 }

exc1-Param-T2-PLP-B-Column-7-Time-Interleave-Length OBJECT-TYPE
	SYNTAX      Integer32
	MAX-ACCESS  read-only
	STATUS      current
	DESCRIPTION
		""
        ::= { exc1-Param-T2-PLP-B-Column-7 8 }

exc1-Param-T2-PLP-B-Column-7-Number-of-FEC-Blocks OBJECT-TYPE
	SYNTAX      Integer32
	MAX-ACCESS  read-only
	STATUS      current
	DESCRIPTION
		""
        ::= { exc1-Param-T2-PLP-B-Column-7 9 }

exc1-Param-T2-PLP-B-Column-7-Transmission-Mode OBJECT-TYPE
	SYNTAX      INTEGER {normal (0), highEfficiency (1)}
	MAX-ACCESS  read-only
	STATUS      current
	DESCRIPTION
		""
        ::= { exc1-Param-T2-PLP-B-Column-7 10 }

exc1-Param-T2-PLP-B-Column-7-ISSY OBJECT-TYPE
	SYNTAX      INTEGER {false(0), true(1)}
	MAX-ACCESS  read-only
	STATUS      current
	DESCRIPTION
		""
        ::= { exc1-Param-T2-PLP-B-Column-7 11 }

exc1-Param-T2-PLP-B-Column-7-NULL-Packet-Deletion OBJECT-TYPE
	SYNTAX      INTEGER {false(0), true(1)}
	MAX-ACCESS  read-only
	STATUS      current
	DESCRIPTION
		""
        ::= { exc1-Param-T2-PLP-B-Column-7 12 }

exc1-Param-T2-PLP-B-Column-7-In-Band-Signaling OBJECT-TYPE
	SYNTAX      INTEGER {false(0), true(1)}
	MAX-ACCESS  read-only
	STATUS      current
	DESCRIPTION
		""
        ::= { exc1-Param-T2-PLP-B-Column-7 13 }

exc1-Param-T2-PLP-B-Column-6-PLP-ID OBJECT-TYPE
	SYNTAX      Integer32
	MAX-ACCESS  read-only
	STATUS      current
	DESCRIPTION
		""
        ::= { exc1-Param-T2-PLP-B-Column-6 1 }

exc1-Param-T2-PLP-B-Column-6-PLP-Type OBJECT-TYPE
	SYNTAX      INTEGER {common (0), type1 (1), type2 (2)}
	MAX-ACCESS  read-only
	STATUS      current
	DESCRIPTION
		""
        ::= { exc1-Param-T2-PLP-B-Column-6 2 }

exc1-Param-T2-PLP-B-Column-6-LDPC OBJECT-TYPE
	SYNTAX      INTEGER {lDPC_16K (0), lDPC_64K (1)}
	MAX-ACCESS  read-only
	STATUS      current
	DESCRIPTION
		""
        ::= { exc1-Param-T2-PLP-B-Column-6 3 }

exc1-Param-T2-PLP-B-Column-6-Coderate OBJECT-TYPE
	SYNTAX      INTEGER {rate_1_2 (0), rate_3_5 (1), rate_2_3 (2), rate_3_4 (3), rate_4_5 (4), rate_5_6 (5)}
	MAX-ACCESS  read-only
	STATUS      current
	DESCRIPTION
		""
        ::= { exc1-Param-T2-PLP-B-Column-6 4 }

exc1-Param-T2-PLP-B-Column-6-Modulation OBJECT-TYPE
	SYNTAX      INTEGER {qPSK (0), qAM_16 (1), qAM_64 (2), qAM_256 (3)}
	MAX-ACCESS  read-only
	STATUS      current
	DESCRIPTION
		""
        ::= { exc1-Param-T2-PLP-B-Column-6 5 }

exc1-Param-T2-PLP-B-Column-6-Rotated-Constellation OBJECT-TYPE
	SYNTAX      INTEGER {notUsed (0), used (1)}
	MAX-ACCESS  read-only
	STATUS      current
	DESCRIPTION
		""
        ::= { exc1-Param-T2-PLP-B-Column-6 6 }

exc1-Param-T2-PLP-B-Column-6-Time-Interleave-Type OBJECT-TYPE
	SYNTAX      INTEGER {oneT2Frame (0), severalT2Frames (1), bypassed (2)}
	MAX-ACCESS  read-only
	STATUS      current
	DESCRIPTION
		""
        ::= { exc1-Param-T2-PLP-B-Column-6 7 }

exc1-Param-T2-PLP-B-Column-6-Time-Interleave-Length OBJECT-TYPE
	SYNTAX      Integer32
	MAX-ACCESS  read-only
	STATUS      current
	DESCRIPTION
		""
        ::= { exc1-Param-T2-PLP-B-Column-6 8 }

exc1-Param-T2-PLP-B-Column-6-Number-of-FEC-Blocks OBJECT-TYPE
	SYNTAX      Integer32
	MAX-ACCESS  read-only
	STATUS      current
	DESCRIPTION
		""
        ::= { exc1-Param-T2-PLP-B-Column-6 9 }

exc1-Param-T2-PLP-B-Column-6-Transmission-Mode OBJECT-TYPE
	SYNTAX      INTEGER {normal (0), highEfficiency (1)}
	MAX-ACCESS  read-only
	STATUS      current
	DESCRIPTION
		""
        ::= { exc1-Param-T2-PLP-B-Column-6 10 }

exc1-Param-T2-PLP-B-Column-6-ISSY OBJECT-TYPE
	SYNTAX      INTEGER {false(0), true(1)}
	MAX-ACCESS  read-only
	STATUS      current
	DESCRIPTION
		""
        ::= { exc1-Param-T2-PLP-B-Column-6 11 }

exc1-Param-T2-PLP-B-Column-6-NULL-Packet-Deletion OBJECT-TYPE
	SYNTAX      INTEGER {false(0), true(1)}
	MAX-ACCESS  read-only
	STATUS      current
	DESCRIPTION
		""
        ::= { exc1-Param-T2-PLP-B-Column-6 12 }

exc1-Param-T2-PLP-B-Column-6-In-Band-Signaling OBJECT-TYPE
	SYNTAX      INTEGER {false(0), true(1)}
	MAX-ACCESS  read-only
	STATUS      current
	DESCRIPTION
		""
        ::= { exc1-Param-T2-PLP-B-Column-6 13 }

exc1-Param-T2-PLP-B-Column-5-PLP-ID OBJECT-TYPE
	SYNTAX      Integer32
	MAX-ACCESS  read-only
	STATUS      current
	DESCRIPTION
		""
        ::= { exc1-Param-T2-PLP-B-Column-5 1 }

exc1-Param-T2-PLP-B-Column-5-PLP-Type OBJECT-TYPE
	SYNTAX      INTEGER {common (0), type1 (1), type2 (2)}
	MAX-ACCESS  read-only
	STATUS      current
	DESCRIPTION
		""
        ::= { exc1-Param-T2-PLP-B-Column-5 2 }

exc1-Param-T2-PLP-B-Column-5-LDPC OBJECT-TYPE
	SYNTAX      INTEGER {lDPC_16K (0), lDPC_64K (1)}
	MAX-ACCESS  read-only
	STATUS      current
	DESCRIPTION
		""
        ::= { exc1-Param-T2-PLP-B-Column-5 3 }

exc1-Param-T2-PLP-B-Column-5-Coderate OBJECT-TYPE
	SYNTAX      INTEGER {rate_1_2 (0), rate_3_5 (1), rate_2_3 (2), rate_3_4 (3), rate_4_5 (4), rate_5_6 (5)}
	MAX-ACCESS  read-only
	STATUS      current
	DESCRIPTION
		""
        ::= { exc1-Param-T2-PLP-B-Column-5 4 }

exc1-Param-T2-PLP-B-Column-5-Modulation OBJECT-TYPE
	SYNTAX      INTEGER {qPSK (0), qAM_16 (1), qAM_64 (2), qAM_256 (3)}
	MAX-ACCESS  read-only
	STATUS      current
	DESCRIPTION
		""
        ::= { exc1-Param-T2-PLP-B-Column-5 5 }

exc1-Param-T2-PLP-B-Column-5-Rotated-Constellation OBJECT-TYPE
	SYNTAX      INTEGER {notUsed (0), used (1)}
	MAX-ACCESS  read-only
	STATUS      current
	DESCRIPTION
		""
        ::= { exc1-Param-T2-PLP-B-Column-5 6 }

exc1-Param-T2-PLP-B-Column-5-Time-Interleave-Type OBJECT-TYPE
	SYNTAX      INTEGER {oneT2Frame (0), severalT2Frames (1), bypassed (2)}
	MAX-ACCESS  read-only
	STATUS      current
	DESCRIPTION
		""
        ::= { exc1-Param-T2-PLP-B-Column-5 7 }

exc1-Param-T2-PLP-B-Column-5-Time-Interleave-Length OBJECT-TYPE
	SYNTAX      Integer32
	MAX-ACCESS  read-only
	STATUS      current
	DESCRIPTION
		""
        ::= { exc1-Param-T2-PLP-B-Column-5 8 }

exc1-Param-T2-PLP-B-Column-5-Number-of-FEC-Blocks OBJECT-TYPE
	SYNTAX      Integer32
	MAX-ACCESS  read-only
	STATUS      current
	DESCRIPTION
		""
        ::= { exc1-Param-T2-PLP-B-Column-5 9 }

exc1-Param-T2-PLP-B-Column-5-Transmission-Mode OBJECT-TYPE
	SYNTAX      INTEGER {normal (0), highEfficiency (1)}
	MAX-ACCESS  read-only
	STATUS      current
	DESCRIPTION
		""
        ::= { exc1-Param-T2-PLP-B-Column-5 10 }

exc1-Param-T2-PLP-B-Column-5-ISSY OBJECT-TYPE
	SYNTAX      INTEGER {false(0), true(1)}
	MAX-ACCESS  read-only
	STATUS      current
	DESCRIPTION
		""
        ::= { exc1-Param-T2-PLP-B-Column-5 11 }

exc1-Param-T2-PLP-B-Column-5-NULL-Packet-Deletion OBJECT-TYPE
	SYNTAX      INTEGER {false(0), true(1)}
	MAX-ACCESS  read-only
	STATUS      current
	DESCRIPTION
		""
        ::= { exc1-Param-T2-PLP-B-Column-5 12 }

exc1-Param-T2-PLP-B-Column-5-In-Band-Signaling OBJECT-TYPE
	SYNTAX      INTEGER {false(0), true(1)}
	MAX-ACCESS  read-only
	STATUS      current
	DESCRIPTION
		""
        ::= { exc1-Param-T2-PLP-B-Column-5 13 }

exc1-Param-T2-PLP-B-Column-4-PLP-ID OBJECT-TYPE
	SYNTAX      Integer32
	MAX-ACCESS  read-only
	STATUS      current
	DESCRIPTION
		""
        ::= { exc1-Param-T2-PLP-B-Column-4 1 }

exc1-Param-T2-PLP-B-Column-4-PLP-Type OBJECT-TYPE
	SYNTAX      INTEGER {common (0), type1 (1), type2 (2)}
	MAX-ACCESS  read-only
	STATUS      current
	DESCRIPTION
		""
        ::= { exc1-Param-T2-PLP-B-Column-4 2 }

exc1-Param-T2-PLP-B-Column-4-LDPC OBJECT-TYPE
	SYNTAX      INTEGER {lDPC_16K (0), lDPC_64K (1)}
	MAX-ACCESS  read-only
	STATUS      current
	DESCRIPTION
		""
        ::= { exc1-Param-T2-PLP-B-Column-4 3 }

exc1-Param-T2-PLP-B-Column-4-Coderate OBJECT-TYPE
	SYNTAX      INTEGER {rate_1_2 (0), rate_3_5 (1), rate_2_3 (2), rate_3_4 (3), rate_4_5 (4), rate_5_6 (5)}
	MAX-ACCESS  read-only
	STATUS      current
	DESCRIPTION
		""
        ::= { exc1-Param-T2-PLP-B-Column-4 4 }

exc1-Param-T2-PLP-B-Column-4-Modulation OBJECT-TYPE
	SYNTAX      INTEGER {qPSK (0), qAM_16 (1), qAM_64 (2), qAM_256 (3)}
	MAX-ACCESS  read-only
	STATUS      current
	DESCRIPTION
		""
        ::= { exc1-Param-T2-PLP-B-Column-4 5 }

exc1-Param-T2-PLP-B-Column-4-Rotated-Constellation OBJECT-TYPE
	SYNTAX      INTEGER {notUsed (0), used (1)}
	MAX-ACCESS  read-only
	STATUS      current
	DESCRIPTION
		""
        ::= { exc1-Param-T2-PLP-B-Column-4 6 }

exc1-Param-T2-PLP-B-Column-4-Time-Interleave-Type OBJECT-TYPE
	SYNTAX      INTEGER {oneT2Frame (0), severalT2Frames (1), bypassed (2)}
	MAX-ACCESS  read-only
	STATUS      current
	DESCRIPTION
		""
        ::= { exc1-Param-T2-PLP-B-Column-4 7 }

exc1-Param-T2-PLP-B-Column-4-Time-Interleave-Length OBJECT-TYPE
	SYNTAX      Integer32
	MAX-ACCESS  read-only
	STATUS      current
	DESCRIPTION
		""
        ::= { exc1-Param-T2-PLP-B-Column-4 8 }

exc1-Param-T2-PLP-B-Column-4-Number-of-FEC-Blocks OBJECT-TYPE
	SYNTAX      Integer32
	MAX-ACCESS  read-only
	STATUS      current
	DESCRIPTION
		""
        ::= { exc1-Param-T2-PLP-B-Column-4 9 }

exc1-Param-T2-PLP-B-Column-4-Transmission-Mode OBJECT-TYPE
	SYNTAX      INTEGER {normal (0), highEfficiency (1)}
	MAX-ACCESS  read-only
	STATUS      current
	DESCRIPTION
		""
        ::= { exc1-Param-T2-PLP-B-Column-4 10 }

exc1-Param-T2-PLP-B-Column-4-ISSY OBJECT-TYPE
	SYNTAX      INTEGER {false(0), true(1)}
	MAX-ACCESS  read-only
	STATUS      current
	DESCRIPTION
		""
        ::= { exc1-Param-T2-PLP-B-Column-4 11 }

exc1-Param-T2-PLP-B-Column-4-NULL-Packet-Deletion OBJECT-TYPE
	SYNTAX      INTEGER {false(0), true(1)}
	MAX-ACCESS  read-only
	STATUS      current
	DESCRIPTION
		""
        ::= { exc1-Param-T2-PLP-B-Column-4 12 }

exc1-Param-T2-PLP-B-Column-4-In-Band-Signaling OBJECT-TYPE
	SYNTAX      INTEGER {false(0), true(1)}
	MAX-ACCESS  read-only
	STATUS      current
	DESCRIPTION
		""
        ::= { exc1-Param-T2-PLP-B-Column-4 13 }

exc1-Param-T2-PLP-B-Column-3-PLP-ID OBJECT-TYPE
	SYNTAX      Integer32
	MAX-ACCESS  read-only
	STATUS      current
	DESCRIPTION
		""
        ::= { exc1-Param-T2-PLP-B-Column-3 1 }

exc1-Param-T2-PLP-B-Column-3-PLP-Type OBJECT-TYPE
	SYNTAX      INTEGER {common (0), type1 (1), type2 (2)}
	MAX-ACCESS  read-only
	STATUS      current
	DESCRIPTION
		""
        ::= { exc1-Param-T2-PLP-B-Column-3 2 }

exc1-Param-T2-PLP-B-Column-3-LDPC OBJECT-TYPE
	SYNTAX      INTEGER {lDPC_16K (0), lDPC_64K (1)}
	MAX-ACCESS  read-only
	STATUS      current
	DESCRIPTION
		""
        ::= { exc1-Param-T2-PLP-B-Column-3 3 }

exc1-Param-T2-PLP-B-Column-3-Coderate OBJECT-TYPE
	SYNTAX      INTEGER {rate_1_2 (0), rate_3_5 (1), rate_2_3 (2), rate_3_4 (3), rate_4_5 (4), rate_5_6 (5)}
	MAX-ACCESS  read-only
	STATUS      current
	DESCRIPTION
		""
        ::= { exc1-Param-T2-PLP-B-Column-3 4 }

exc1-Param-T2-PLP-B-Column-3-Modulation OBJECT-TYPE
	SYNTAX      INTEGER {qPSK (0), qAM_16 (1), qAM_64 (2), qAM_256 (3)}
	MAX-ACCESS  read-only
	STATUS      current
	DESCRIPTION
		""
        ::= { exc1-Param-T2-PLP-B-Column-3 5 }

exc1-Param-T2-PLP-B-Column-3-Rotated-Constellation OBJECT-TYPE
	SYNTAX      INTEGER {notUsed (0), used (1)}
	MAX-ACCESS  read-only
	STATUS      current
	DESCRIPTION
		""
        ::= { exc1-Param-T2-PLP-B-Column-3 6 }

exc1-Param-T2-PLP-B-Column-3-Time-Interleave-Type OBJECT-TYPE
	SYNTAX      INTEGER {oneT2Frame (0), severalT2Frames (1), bypassed (2)}
	MAX-ACCESS  read-only
	STATUS      current
	DESCRIPTION
		""
        ::= { exc1-Param-T2-PLP-B-Column-3 7 }

exc1-Param-T2-PLP-B-Column-3-Time-Interleave-Length OBJECT-TYPE
	SYNTAX      Integer32
	MAX-ACCESS  read-only
	STATUS      current
	DESCRIPTION
		""
        ::= { exc1-Param-T2-PLP-B-Column-3 8 }

exc1-Param-T2-PLP-B-Column-3-Number-of-FEC-Blocks OBJECT-TYPE
	SYNTAX      Integer32
	MAX-ACCESS  read-only
	STATUS      current
	DESCRIPTION
		""
        ::= { exc1-Param-T2-PLP-B-Column-3 9 }

exc1-Param-T2-PLP-B-Column-3-Transmission-Mode OBJECT-TYPE
	SYNTAX      INTEGER {normal (0), highEfficiency (1)}
	MAX-ACCESS  read-only
	STATUS      current
	DESCRIPTION
		""
        ::= { exc1-Param-T2-PLP-B-Column-3 10 }

exc1-Param-T2-PLP-B-Column-3-ISSY OBJECT-TYPE
	SYNTAX      INTEGER {false(0), true(1)}
	MAX-ACCESS  read-only
	STATUS      current
	DESCRIPTION
		""
        ::= { exc1-Param-T2-PLP-B-Column-3 11 }

exc1-Param-T2-PLP-B-Column-3-NULL-Packet-Deletion OBJECT-TYPE
	SYNTAX      INTEGER {false(0), true(1)}
	MAX-ACCESS  read-only
	STATUS      current
	DESCRIPTION
		""
        ::= { exc1-Param-T2-PLP-B-Column-3 12 }

exc1-Param-T2-PLP-B-Column-3-In-Band-Signaling OBJECT-TYPE
	SYNTAX      INTEGER {false(0), true(1)}
	MAX-ACCESS  read-only
	STATUS      current
	DESCRIPTION
		""
        ::= { exc1-Param-T2-PLP-B-Column-3 13 }

exc1-Param-T2-PLP-B-Column-2-PLP-ID OBJECT-TYPE
	SYNTAX      Integer32
	MAX-ACCESS  read-only
	STATUS      current
	DESCRIPTION
		""
        ::= { exc1-Param-T2-PLP-B-Column-2 1 }

exc1-Param-T2-PLP-B-Column-2-PLP-Type OBJECT-TYPE
	SYNTAX      INTEGER {common (0), type1 (1), type2 (2)}
	MAX-ACCESS  read-only
	STATUS      current
	DESCRIPTION
		""
        ::= { exc1-Param-T2-PLP-B-Column-2 2 }

exc1-Param-T2-PLP-B-Column-2-LDPC OBJECT-TYPE
	SYNTAX      INTEGER {lDPC_16K (0), lDPC_64K (1)}
	MAX-ACCESS  read-only
	STATUS      current
	DESCRIPTION
		""
        ::= { exc1-Param-T2-PLP-B-Column-2 3 }

exc1-Param-T2-PLP-B-Column-2-Coderate OBJECT-TYPE
	SYNTAX      INTEGER {rate_1_2 (0), rate_3_5 (1), rate_2_3 (2), rate_3_4 (3), rate_4_5 (4), rate_5_6 (5)}
	MAX-ACCESS  read-only
	STATUS      current
	DESCRIPTION
		""
        ::= { exc1-Param-T2-PLP-B-Column-2 4 }

exc1-Param-T2-PLP-B-Column-2-Modulation OBJECT-TYPE
	SYNTAX      INTEGER {qPSK (0), qAM_16 (1), qAM_64 (2), qAM_256 (3)}
	MAX-ACCESS  read-only
	STATUS      current
	DESCRIPTION
		""
        ::= { exc1-Param-T2-PLP-B-Column-2 5 }

exc1-Param-T2-PLP-B-Column-2-Rotated-Constellation OBJECT-TYPE
	SYNTAX      INTEGER {notUsed (0), used (1)}
	MAX-ACCESS  read-only
	STATUS      current
	DESCRIPTION
		""
        ::= { exc1-Param-T2-PLP-B-Column-2 6 }

exc1-Param-T2-PLP-B-Column-2-Time-Interleave-Type OBJECT-TYPE
	SYNTAX      INTEGER {oneT2Frame (0), severalT2Frames (1), bypassed (2)}
	MAX-ACCESS  read-only
	STATUS      current
	DESCRIPTION
		""
        ::= { exc1-Param-T2-PLP-B-Column-2 7 }

exc1-Param-T2-PLP-B-Column-2-Time-Interleave-Length OBJECT-TYPE
	SYNTAX      Integer32
	MAX-ACCESS  read-only
	STATUS      current
	DESCRIPTION
		""
        ::= { exc1-Param-T2-PLP-B-Column-2 8 }

exc1-Param-T2-PLP-B-Column-2-Number-of-FEC-Blocks OBJECT-TYPE
	SYNTAX      Integer32
	MAX-ACCESS  read-only
	STATUS      current
	DESCRIPTION
		""
        ::= { exc1-Param-T2-PLP-B-Column-2 9 }

exc1-Param-T2-PLP-B-Column-2-Transmission-Mode OBJECT-TYPE
	SYNTAX      INTEGER {normal (0), highEfficiency (1)}
	MAX-ACCESS  read-only
	STATUS      current
	DESCRIPTION
		""
        ::= { exc1-Param-T2-PLP-B-Column-2 10 }

exc1-Param-T2-PLP-B-Column-2-ISSY OBJECT-TYPE
	SYNTAX      INTEGER {false(0), true(1)}
	MAX-ACCESS  read-only
	STATUS      current
	DESCRIPTION
		""
        ::= { exc1-Param-T2-PLP-B-Column-2 11 }

exc1-Param-T2-PLP-B-Column-2-NULL-Packet-Deletion OBJECT-TYPE
	SYNTAX      INTEGER {false(0), true(1)}
	MAX-ACCESS  read-only
	STATUS      current
	DESCRIPTION
		""
        ::= { exc1-Param-T2-PLP-B-Column-2 12 }

exc1-Param-T2-PLP-B-Column-2-In-Band-Signaling OBJECT-TYPE
	SYNTAX      INTEGER {false(0), true(1)}
	MAX-ACCESS  read-only
	STATUS      current
	DESCRIPTION
		""
        ::= { exc1-Param-T2-PLP-B-Column-2 13 }

exc1-Param-T2-PLP-B-Column-1-PLP-ID OBJECT-TYPE
	SYNTAX      Integer32
	MAX-ACCESS  read-only
	STATUS      current
	DESCRIPTION
		""
        ::= { exc1-Param-T2-PLP-B-Column-1 1 }

exc1-Param-T2-PLP-B-Column-1-PLP-Type OBJECT-TYPE
	SYNTAX      INTEGER {common (0), type1 (1), type2 (2)}
	MAX-ACCESS  read-only
	STATUS      current
	DESCRIPTION
		""
        ::= { exc1-Param-T2-PLP-B-Column-1 2 }

exc1-Param-T2-PLP-B-Column-1-LDPC OBJECT-TYPE
	SYNTAX      INTEGER {lDPC_16K (0), lDPC_64K (1)}
	MAX-ACCESS  read-only
	STATUS      current
	DESCRIPTION
		""
        ::= { exc1-Param-T2-PLP-B-Column-1 3 }

exc1-Param-T2-PLP-B-Column-1-Coderate OBJECT-TYPE
	SYNTAX      INTEGER {rate_1_2 (0), rate_3_5 (1), rate_2_3 (2), rate_3_4 (3), rate_4_5 (4), rate_5_6 (5)}
	MAX-ACCESS  read-only
	STATUS      current
	DESCRIPTION
		""
        ::= { exc1-Param-T2-PLP-B-Column-1 4 }

exc1-Param-T2-PLP-B-Column-1-Modulation OBJECT-TYPE
	SYNTAX      INTEGER {qPSK (0), qAM_16 (1), qAM_64 (2), qAM_256 (3)}
	MAX-ACCESS  read-only
	STATUS      current
	DESCRIPTION
		""
        ::= { exc1-Param-T2-PLP-B-Column-1 5 }

exc1-Param-T2-PLP-B-Column-1-Rotated-Constellation OBJECT-TYPE
	SYNTAX      INTEGER {notUsed (0), used (1)}
	MAX-ACCESS  read-only
	STATUS      current
	DESCRIPTION
		""
        ::= { exc1-Param-T2-PLP-B-Column-1 6 }

exc1-Param-T2-PLP-B-Column-1-Time-Interleave-Type OBJECT-TYPE
	SYNTAX      INTEGER {oneT2Frame (0), severalT2Frames (1), bypassed (2)}
	MAX-ACCESS  read-only
	STATUS      current
	DESCRIPTION
		""
        ::= { exc1-Param-T2-PLP-B-Column-1 7 }

exc1-Param-T2-PLP-B-Column-1-Time-Interleave-Length OBJECT-TYPE
	SYNTAX      Integer32
	MAX-ACCESS  read-only
	STATUS      current
	DESCRIPTION
		""
        ::= { exc1-Param-T2-PLP-B-Column-1 8 }

exc1-Param-T2-PLP-B-Column-1-Number-of-FEC-Blocks OBJECT-TYPE
	SYNTAX      Integer32
	MAX-ACCESS  read-only
	STATUS      current
	DESCRIPTION
		""
        ::= { exc1-Param-T2-PLP-B-Column-1 9 }

exc1-Param-T2-PLP-B-Column-1-Transmission-Mode OBJECT-TYPE
	SYNTAX      INTEGER {normal (0), highEfficiency (1)}
	MAX-ACCESS  read-only
	STATUS      current
	DESCRIPTION
		""
        ::= { exc1-Param-T2-PLP-B-Column-1 10 }

exc1-Param-T2-PLP-B-Column-1-ISSY OBJECT-TYPE
	SYNTAX      INTEGER {false(0), true(1)}
	MAX-ACCESS  read-only
	STATUS      current
	DESCRIPTION
		""
        ::= { exc1-Param-T2-PLP-B-Column-1 11 }

exc1-Param-T2-PLP-B-Column-1-NULL-Packet-Deletion OBJECT-TYPE
	SYNTAX      INTEGER {false(0), true(1)}
	MAX-ACCESS  read-only
	STATUS      current
	DESCRIPTION
		""
        ::= { exc1-Param-T2-PLP-B-Column-1 12 }

exc1-Param-T2-PLP-B-Column-1-In-Band-Signaling OBJECT-TYPE
	SYNTAX      INTEGER {false(0), true(1)}
	MAX-ACCESS  read-only
	STATUS      current
	DESCRIPTION
		""
        ::= { exc1-Param-T2-PLP-B-Column-1 13 }

exc1-Param-T2-PLP-A-PLP-ID OBJECT-TYPE
	SYNTAX      Integer32
	MAX-ACCESS  read-write
	STATUS      current
	DESCRIPTION
		""
        ::= { exc1-Param-T2-PLP-System-A 1 }

exc1-Param-T2-PLP-A-LDPC OBJECT-TYPE
	SYNTAX      INTEGER {lDPC_16K (0), lDPC_64K (1)}
	MAX-ACCESS  read-write
	STATUS      current
	DESCRIPTION
		""
        ::= { exc1-Param-T2-PLP-System-A 2 }

exc1-Param-T2-PLP-A-Coderate OBJECT-TYPE
	SYNTAX      INTEGER {rate_1_2 (0), rate_3_5 (1), rate_2_3 (2), rate_3_4 (3), rate_4_5 (4), rate_5_6 (5)}
	MAX-ACCESS  read-write
	STATUS      current
	DESCRIPTION
		""
        ::= { exc1-Param-T2-PLP-System-A 3 }

exc1-Param-T2-PLP-A-Modulation OBJECT-TYPE
	SYNTAX      INTEGER {qPSK (0), qAM_16 (1), qAM_64 (2), qAM_256 (3)}
	MAX-ACCESS  read-write
	STATUS      current
	DESCRIPTION
		""
        ::= { exc1-Param-T2-PLP-System-A 4 }

exc1-Param-T2-PLP-A-Rotated-Constellation OBJECT-TYPE
	SYNTAX      INTEGER {notUsed (0), used (1)}
	MAX-ACCESS  read-write
	STATUS      current
	DESCRIPTION
		""
        ::= { exc1-Param-T2-PLP-System-A 5 }

exc1-Param-T2-PLP-A-Time-Interleave-Type OBJECT-TYPE
	SYNTAX      INTEGER {oneT2Frame (0), severalT2Frames (1), bypassed (2)}
	MAX-ACCESS  read-write
	STATUS      current
	DESCRIPTION
		""
        ::= { exc1-Param-T2-PLP-System-A 6 }

exc1-Param-T2-PLP-A-Time-Interleave-Length OBJECT-TYPE
	SYNTAX      Integer32
	MAX-ACCESS  read-write
	STATUS      current
	DESCRIPTION
		""
        ::= { exc1-Param-T2-PLP-System-A 7 }

exc1-Param-T2-PLP-A-Number-of-FEC-Blocks OBJECT-TYPE
	SYNTAX      Integer32
	MAX-ACCESS  read-write
	STATUS      current
	DESCRIPTION
		""
        ::= { exc1-Param-T2-PLP-System-A 8 }

exc1-Param-T2-PLP-A-ISSY OBJECT-TYPE
	SYNTAX      INTEGER {false(0), true(1)}
	MAX-ACCESS  read-write
	STATUS      current
	DESCRIPTION
		""
        ::= { exc1-Param-T2-PLP-System-A 9 }

exc1-Param-T2-PLP-A-NULL-Packet-Deletion OBJECT-TYPE
	SYNTAX      INTEGER {false(0), true(1)}
	MAX-ACCESS  read-write
	STATUS      current
	DESCRIPTION
		""
        ::= { exc1-Param-T2-PLP-System-A 10 }

exc1-Param-T2-Settings-Network-System-ID OBJECT-TYPE
	SYNTAX      Integer32
	MAX-ACCESS  read-write
	STATUS      current
	DESCRIPTION
		""
        ::= { exc1-Param-T2-Settings-Network 1 }

exc1-Param-T2-Settings-Network-Network-ID OBJECT-TYPE
	SYNTAX      Integer32
	MAX-ACCESS  read-write
	STATUS      current
	DESCRIPTION
		""
        ::= { exc1-Param-T2-Settings-Network 2 }

exc1-Param-T2-Settings-Network-Cell-ID OBJECT-TYPE
	SYNTAX      Integer32
	MAX-ACCESS  read-write
	STATUS      current
	DESCRIPTION
		""
        ::= { exc1-Param-T2-Settings-Network 3 }

exc1-Param-T2-Settings-Network-Transmitter-ID OBJECT-TYPE
	SYNTAX      Integer32
	MAX-ACCESS  read-write
	STATUS      current
	DESCRIPTION
		""
        ::= { exc1-Param-T2-Settings-Network 4 }

exc1-Param-T2-Settings-Network-Cell-ID-Set-by-User OBJECT-TYPE
	SYNTAX      INTEGER {false(0), true(1)}
	MAX-ACCESS  read-write
	STATUS      current
	DESCRIPTION
		""
        ::= { exc1-Param-T2-Settings-Network 5 }

exc1-Param-T2-Settings-PAPR-Tone-Reservation OBJECT-TYPE
	SYNTAX      INTEGER {disabled (0), enabled (1)}
	MAX-ACCESS  read-write
	STATUS      current
	DESCRIPTION
		""
        ::= { exc1-Param-T2-Settings-PAPR 1 }

exc1-Param-T2-Settings-Structure-Number-of-T2-Frames OBJECT-TYPE
	SYNTAX      Integer32
	MAX-ACCESS  read-write
	STATUS      current
	DESCRIPTION
		""
        ::= { exc1-Param-T2-Settings-Frame-Structure 1 }

exc1-Param-T2-Settings-Structure-Number-of-OFDM-Symbols OBJECT-TYPE
	SYNTAX      Integer32
	MAX-ACCESS  read-write
	STATUS      current
	DESCRIPTION
		""
        ::= { exc1-Param-T2-Settings-Frame-Structure 2 }

exc1-Param-T2-Settings-Structure-Signaling-Constellation OBJECT-TYPE
	SYNTAX      INTEGER {bPSK (0), qPSK (1), qAM_16 (2), qAM_64 (3)}
	MAX-ACCESS  read-write
	STATUS      current
	DESCRIPTION
		""
        ::= { exc1-Param-T2-Settings-Frame-Structure 3 }

exc1-Param-T2-Settings-Structure-Standard-Version OBJECT-TYPE
	SYNTAX      INTEGER {version_1_1_1 (0), version_1_2_1 (1), version_1_3_1 (2)}
	MAX-ACCESS  read-only
	STATUS      current
	DESCRIPTION
		""
        ::= { exc1-Param-T2-Settings-Frame-Structure 4 }

exc1-Param-T2-Settings-Modulation-Bandwidth OBJECT-TYPE
	SYNTAX      INTEGER {band_1_7Mhz (0), band_5Mhz (1), band_6Mhz (2), band_7Mhz (3), band_8Mhz (4), band_10Mhz (5)}
	MAX-ACCESS  read-write
	STATUS      current
	DESCRIPTION
		""
        ::= { exc1-Param-T2-Settings-Frame-Modulation 1 }

exc1-Param-T2-Settings-Modulation-FFT-Size OBJECT-TYPE
	SYNTAX      INTEGER {fFT_2K (0), fFT_8K (1), fFT_4K (2), fFT_1K (3), fFT_16K (4), fFT_32K (5)}
	MAX-ACCESS  read-write
	STATUS      current
	DESCRIPTION
		""
        ::= { exc1-Param-T2-Settings-Frame-Modulation 2 }

exc1-Param-T2-Settings-Modulation-Bandwidth-Extension OBJECT-TYPE
	SYNTAX      INTEGER {notUsed (0), used (1)}
	MAX-ACCESS  read-write
	STATUS      current
	DESCRIPTION
		""
        ::= { exc1-Param-T2-Settings-Frame-Modulation 3 }

exc1-Param-T2-Settings-Modulation-Guard-Interval OBJECT-TYPE
	SYNTAX      INTEGER {interval_1_32 (0), interval_1_16 (1), interval_1_8 (2), interval_1_4 (3), interval_1_128 (4), interval_19_128 (5), interval_19_256 (6)}
	MAX-ACCESS  read-write
	STATUS      current
	DESCRIPTION
		""
        ::= { exc1-Param-T2-Settings-Frame-Modulation 4 }

exc1-Param-T2-Settings-Modulation-Pilot-Pattern OBJECT-TYPE
	SYNTAX      INTEGER {pP1 (0), pP2 (1), pP3 (2), pP4 (3), pP5 (4), pP6 (5), pP7 (6), pP8 (7)}
	MAX-ACCESS  read-write
	STATUS      current
	DESCRIPTION
		""
        ::= { exc1-Param-T2-Settings-Frame-Modulation 5 }

exc1-Param-T2-Input-PID-of-MPEG2-TS-Packet OBJECT-TYPE
	SYNTAX      Integer32
	MAX-ACCESS  read-write
	STATUS      current
	DESCRIPTION
		""
        ::= { exc1-Param-T2-InputStream 1 }

exc1-Param-T2-Input-Input-Type OBJECT-TYPE
	SYNTAX      INTEGER {singlePLP (0), multiPLP (1)}
	MAX-ACCESS  read-write
	STATUS      current
	DESCRIPTION
		""
        ::= { exc1-Param-T2-InputStream 2 }

exc1-Param-T2-Input-Transmission-Mode OBJECT-TYPE
	SYNTAX      INTEGER {normal (0), highEfficiency (1)}
	MAX-ACCESS  read-write
	STATUS      current
	DESCRIPTION
		""
        ::= { exc1-Param-T2-InputStream 3 }

exc1-Param-T2-SFN-SFN-Synchronization OBJECT-TYPE
	SYNTAX      INTEGER {off (0), on (1)}
	MAX-ACCESS  read-write
	STATUS      current
	DESCRIPTION
		""
        ::= { exc1-Param-T2-SFN 1 }

exc1-Param-T2-SFN-SFN-Local-Time-Offset OBJECT-TYPE
	SYNTAX      Integer32
	MAX-ACCESS  read-write
	STATUS      current
	DESCRIPTION
		""
        ::= { exc1-Param-T2-SFN 2 }

exc1-Param-T2-SFN-SFN-Extended-Time-Offset OBJECT-TYPE
	SYNTAX      Integer32
	MAX-ACCESS  read-write
	STATUS      current
	DESCRIPTION
		""
        ::= { exc1-Param-T2-SFN 3 }

exc1-Param-T2-SFN-Output-Mode OBJECT-TYPE
	SYNTAX      INTEGER {sISO (0), mISO (1)}
	MAX-ACCESS  read-write
	STATUS      current
	DESCRIPTION
		""
        ::= { exc1-Param-T2-SFN 4 }

exc1-Param-T2-SFN-MISO-Group OBJECT-TYPE
	SYNTAX      INTEGER {group_1 (0), group_2 (1)}
	MAX-ACCESS  read-write
	STATUS      current
	DESCRIPTION
		""
        ::= { exc1-Param-T2-SFN 5 }

exc1-Param-T2-SFN-MISO-Group-Set-by-User OBJECT-TYPE
	SYNTAX      INTEGER {false(0), true(1)}
	MAX-ACCESS  read-write
	STATUS      current
	DESCRIPTION
		""
        ::= { exc1-Param-T2-SFN 6 }

exc1-Param-T-MIP-Control-MIP-Control OBJECT-TYPE
	SYNTAX      INTEGER {notEnabled (0), mandatory (1), mandatoryOptional (2)}
	MAX-ACCESS  read-write
	STATUS      current
	DESCRIPTION
		""
        ::= { exc1-Param-T-MIP-Control 1 }

exc1-Param-T-MIP-Control-Transmitter-ID OBJECT-TYPE
	SYNTAX      Integer32
	MAX-ACCESS  read-write
	STATUS      current
	DESCRIPTION
		""
        ::= { exc1-Param-T-MIP-Control 2 }

exc1-Param-T-MIP-Control-Mute-on-MIP-Synchro-Warning OBJECT-TYPE
	SYNTAX      INTEGER {manual (0), auto (1)}
	MAX-ACCESS  read-write
	STATUS      current
	DESCRIPTION
		""
        ::= { exc1-Param-T-MIP-Control 3 }

exc1-Param-T-MIP-Control-Resync-on-MIP-Synchro-Error OBJECT-TYPE
	SYNTAX      INTEGER {manual (0), auto (1)}
	MAX-ACCESS  read-write
	STATUS      current
	DESCRIPTION
		""
        ::= { exc1-Param-T-MIP-Control 4 }

exc1-Param-T-MIP-Control-Mute-Timeout-before-Mute-Request OBJECT-TYPE
	SYNTAX      Integer32
	MAX-ACCESS  read-write
	STATUS      current
	DESCRIPTION
		""
        ::= { exc1-Param-T-MIP-Control 5 }

exc1-Param-T-MIP-Control-Unmute-Threshold-before-Unmute-Request OBJECT-TYPE
	SYNTAX      Integer32
	MAX-ACCESS  read-write
	STATUS      current
	DESCRIPTION
		""
        ::= { exc1-Param-T-MIP-Control 6 }

exc1-Param-T-MIP-Control-Restart-Timeout-before-Restart-Request OBJECT-TYPE
	SYNTAX      Integer32
	MAX-ACCESS  read-write
	STATUS      current
	DESCRIPTION
		""
        ::= { exc1-Param-T-MIP-Control 7 }

exc1-Param-T-Specific-Config-Mute-on-MIP-is-Missing OBJECT-TYPE
	SYNTAX      INTEGER {false(0), true(1)}
	MAX-ACCESS  read-write
	STATUS      current
	DESCRIPTION
		""
        ::= { exc1-Param-T-Specific-Config 1 }

exc1-Param-T-Specific-Config-Network-Delay-Error OBJECT-TYPE
	SYNTAX      INTEGER {false(0), true(1)}
	MAX-ACCESS  read-write
	STATUS      current
	DESCRIPTION
		""
        ::= { exc1-Param-T-Specific-Config 2 }

exc1-Param-T-TPS-CELL-ID OBJECT-TYPE
	SYNTAX      Integer32
	MAX-ACCESS  read-write
	STATUS      current
	DESCRIPTION
		""
        ::= { exc1-Param-T-TPS 1 }

exc1-Param-T-TPS-CELL-ID-Insertion OBJECT-TYPE
	SYNTAX      INTEGER {deactivated (0), activated (1)}
	MAX-ACCESS  read-write
	STATUS      current
	DESCRIPTION
		""
        ::= { exc1-Param-T-TPS 2 }

exc1-Param-T-TPS-DVB-H-Signaling OBJECT-TYPE
	SYNTAX      INTEGER {off (0), on (1)}
	MAX-ACCESS  read-write
	STATUS      current
	DESCRIPTION
		""
        ::= { exc1-Param-T-TPS 3 }

exc1-Param-T-TPS-Time-Slicing-on-HP OBJECT-TYPE
	SYNTAX      INTEGER {notUsed (0), used (1)}
	MAX-ACCESS  read-write
	STATUS      current
	DESCRIPTION
		""
        ::= { exc1-Param-T-TPS 4 }

exc1-Param-T-TPS-MPE-FEC-on-HP OBJECT-TYPE
	SYNTAX      INTEGER {notUsed (0), used (1)}
	MAX-ACCESS  read-write
	STATUS      current
	DESCRIPTION
		""
        ::= { exc1-Param-T-TPS 5 }

exc1-Param-T-TPS-Time-Slicing-on-LP OBJECT-TYPE
	SYNTAX      INTEGER {notUsed (0), used (1)}
	MAX-ACCESS  read-write
	STATUS      current
	DESCRIPTION
		""
        ::= { exc1-Param-T-TPS 6 }

exc1-Param-T-TPS-MPE-FEC-on-LP OBJECT-TYPE
	SYNTAX      INTEGER {notUsed (0), used (1)}
	MAX-ACCESS  read-write
	STATUS      current
	DESCRIPTION
		""
        ::= { exc1-Param-T-TPS 7 }

exc1-Param-T-TPS-Special-Bits OBJECT-TYPE
	SYNTAX      Integer32
	MAX-ACCESS  read-write
	STATUS      current
	DESCRIPTION
		""
        ::= { exc1-Param-T-TPS 8 }

exc1-Param-T-Mode-Bandwidth OBJECT-TYPE
	SYNTAX      INTEGER {band_5Mhz (0), band_6Mhz (1), band_7Mhz (2), band_8Mhz (3)}
	MAX-ACCESS  read-write
	STATUS      current
	DESCRIPTION
		""
        ::= { exc1-Param-T-Mode 1 }

exc1-Param-T-Mode-FFT-Mode OBJECT-TYPE
	SYNTAX      INTEGER {fFT_2K (0), fFT_8K (1), fFT_4K (2)}
	MAX-ACCESS  read-write
	STATUS      current
	DESCRIPTION
		""
        ::= { exc1-Param-T-Mode 2 }

exc1-Param-T-Mode-Guard-Interval OBJECT-TYPE
	SYNTAX      INTEGER {interval_1_32 (0), interval_1_16 (1), interval_1_8 (2), interval_1_4 (3)}
	MAX-ACCESS  read-write
	STATUS      current
	DESCRIPTION
		""
        ::= { exc1-Param-T-Mode 3 }

exc1-Param-T-Mode-Constellation OBJECT-TYPE
	SYNTAX      INTEGER {qPSK (0), qAM_16 (1), qAM_64 (2)}
	MAX-ACCESS  read-write
	STATUS      current
	DESCRIPTION
		""
        ::= { exc1-Param-T-Mode 4 }

exc1-Param-T-Mode-Inner-Interleaver OBJECT-TYPE
	SYNTAX      INTEGER {native (0), inDepth (1)}
	MAX-ACCESS  read-write
	STATUS      current
	DESCRIPTION
		""
        ::= { exc1-Param-T-Mode 5 }

exc1-Param-T-Mode-Modulation OBJECT-TYPE
	SYNTAX      INTEGER {nonHierarchical (0), hierarAlpha1 (1), hierarAlpha2 (2), hierarAlpha4 (3)}
	MAX-ACCESS  read-write
	STATUS      current
	DESCRIPTION
		""
        ::= { exc1-Param-T-Mode 6 }

exc1-Param-T-Mode-HP-Coderate OBJECT-TYPE
	SYNTAX      INTEGER {rate_1_2 (0), rate_2_3 (1), rate_3_4 (2), rate_5_6 (3), rate_7_8 (4)}
	MAX-ACCESS  read-write
	STATUS      current
	DESCRIPTION
		""
        ::= { exc1-Param-T-Mode 7 }

exc1-Param-T-Mode-LP-Coderate OBJECT-TYPE
	SYNTAX      INTEGER {rate_1_2 (0), rate_2_3 (1), rate_3_4 (2), rate_5_6 (3), rate_7_8 (4)}
	MAX-ACCESS  read-write
	STATUS      current
	DESCRIPTION
		""
        ::= { exc1-Param-T-Mode 8 }

exc1-Param-T-SFN-Synchronization OBJECT-TYPE
	SYNTAX      INTEGER {mFN (0), sFN (1)}
	MAX-ACCESS  read-write
	STATUS      current
	DESCRIPTION
		""
        ::= { exc1-Param-T-SFN 1 }

exc1-Param-T-SFN-Fine-Time-Offset OBJECT-TYPE
	SYNTAX      Integer32
	MAX-ACCESS  read-write
	STATUS      current
	DESCRIPTION
		""
        ::= { exc1-Param-T-SFN 2 }

exc1-Param-T-SFN-Static-Time-Offset OBJECT-TYPE
	SYNTAX      Integer32
	MAX-ACCESS  read-write
	STATUS      current
	DESCRIPTION
		""
        ::= { exc1-Param-T-SFN 3 }

exc1-Param-T-SFN-Resynchronize-SFN OBJECT-TYPE
	SYNTAX      INTEGER {false(0), true(1)}
	MAX-ACCESS  read-write
	STATUS      current
	DESCRIPTION
		""
        ::= { exc1-Param-T-SFN 4 }

exc1-Param-T-MFN-Bitrate-Adaptation OBJECT-TYPE
	SYNTAX      INTEGER {false(0), true(1)}
	MAX-ACCESS  read-write
	STATUS      current
	DESCRIPTION
		""
        ::= { exc1-Param-T-MFN 1 }

exc1-Param-T-MFN-NIT-Table-Update OBJECT-TYPE
	SYNTAX      INTEGER {false(0), true(1)}
	MAX-ACCESS  read-write
	STATUS      current
	DESCRIPTION
		""
        ::= { exc1-Param-T-MFN 2 }

exc1-Param-T-MFN-Frequency-in-NIT-Table OBJECT-TYPE
	SYNTAX      Integer32
	MAX-ACCESS  read-write
	STATUS      current
	DESCRIPTION
		""
        ::= { exc1-Param-T-MFN 3 }

exc1-Param-Output-Starting-Delay OBJECT-TYPE
	SYNTAX      Integer32
	MAX-ACCESS  read-write
	STATUS      current
	DESCRIPTION
		""
        ::= { exc1-Param-Output 1 }

exc1-Param-Output-Gain-Offset OBJECT-TYPE
	SYNTAX      Integer32
	MAX-ACCESS  read-write
	STATUS      current
	DESCRIPTION
		""
        ::= { exc1-Param-Output 2 }

exc1-Param-Output-Attenuation OBJECT-TYPE
	SYNTAX      Integer32
	MAX-ACCESS  read-write
	STATUS      current
	DESCRIPTION
		""
        ::= { exc1-Param-Output 3 }

exc1-Param-Output-Is-Mute OBJECT-TYPE
	SYNTAX      INTEGER {false(0), true(1)}
	MAX-ACCESS  read-write
	STATUS      current
	DESCRIPTION
		""
        ::= { exc1-Param-Output 4 }

exc1-Param-Output-Is-RF-Maintain-On-Input-Stream OBJECT-TYPE
	SYNTAX      INTEGER {false(0), true(1)}
	MAX-ACCESS  read-write
	STATUS      current
	DESCRIPTION
		""
        ::= { exc1-Param-Output 5 }

exc1-Param-Output-Crest-Factor-Required OBJECT-TYPE
	SYNTAX      Integer32
	MAX-ACCESS  read-write
	STATUS      current
	DESCRIPTION
		""
        ::= { exc1-Param-Output 6 }

exc1-Param-Output-Crest-Factor-Optimization OBJECT-TYPE
	SYNTAX      Integer32
	MAX-ACCESS  read-write
	STATUS      current
	DESCRIPTION
		""
        ::= { exc1-Param-Output 7 }

exc1-Param-Output-Protection-Clipping OBJECT-TYPE
	SYNTAX      Integer32
	MAX-ACCESS  read-write
	STATUS      current
	DESCRIPTION
		""
        ::= { exc1-Param-Output 8 }

exc1-Param-Output-Linear-Precorrection OBJECT-TYPE
	SYNTAX      INTEGER {bypassed (0), enabled (1)}
	MAX-ACCESS  read-write
	STATUS      current
	DESCRIPTION
		""
        ::= { exc1-Param-Output 9 }

exc1-Param-Output-Non-Linear-Precorrection OBJECT-TYPE
	SYNTAX      INTEGER {bypassed (0), enabled (1)}
	MAX-ACCESS  read-write
	STATUS      current
	DESCRIPTION
		""
        ::= { exc1-Param-Output 10 }

exc1-Param-Output-Mute-on-PLL-Unlocked OBJECT-TYPE
	SYNTAX      INTEGER {false(0), true(1)}
	MAX-ACCESS  read-write
	STATUS      current
	DESCRIPTION
		""
        ::= { exc1-Param-Output 11 }

exc1-Param-Output-TV-Channel OBJECT-TYPE
	SYNTAX      Integer32
	MAX-ACCESS  read-only
	STATUS      current
	DESCRIPTION
		""
        ::= { exc1-Param-Output 12 }

exc1-Param-Output-Is-RF-Maintain-On-PPS-Resync OBJECT-TYPE
	SYNTAX      INTEGER {false(0), true(1)}
	MAX-ACCESS  read-write
	STATUS      current
	DESCRIPTION
		""
        ::= { exc1-Param-Output 13 }

exc1-Param-Input-Clever-IP-Primary-Input OBJECT-TYPE
	SYNTAX      INTEGER {iP1 (0), iP2 (1)}
	MAX-ACCESS  read-write
	STATUS      current
	DESCRIPTION
		""
        ::= { exc1-Param-Input-Clever-Switch-IP-Parameters 1 }

exc1-Param-Input-Clever-IP-Clever-Switch-IP OBJECT-TYPE
	SYNTAX      INTEGER {false(0), true(1)}
	MAX-ACCESS  read-write
	STATUS      current
	DESCRIPTION
		""
        ::= { exc1-Param-Input-Clever-Switch-IP-Parameters 2 }

exc1-Param-Input-Clever-IP-Auto-Switch-Back OBJECT-TYPE
	SYNTAX      INTEGER {false(0), true(1)}
	MAX-ACCESS  read-write
	STATUS      current
	DESCRIPTION
		""
        ::= { exc1-Param-Input-Clever-Switch-IP-Parameters 3 }

exc1-Param-Input-Clever-IP-RTP-Packet-Timeout OBJECT-TYPE
	SYNTAX      Integer32
	MAX-ACCESS  read-write
	STATUS      current
	DESCRIPTION
		""
        ::= { exc1-Param-Input-Clever-Switch-IP-Parameters 4 }

exc1-Param-Input-Clever-IP-RTP-Valid-Packet-Time OBJECT-TYPE
	SYNTAX      Integer32
	MAX-ACCESS  read-write
	STATUS      current
	DESCRIPTION
		""
        ::= { exc1-Param-Input-Clever-Switch-IP-Parameters 5 }

exc1-Param-Input-IP-2-IGMP-Mode OBJECT-TYPE
	SYNTAX      INTEGER {exclude (0), include (1)}
	MAX-ACCESS  read-write
	STATUS      current
	DESCRIPTION
		""
        ::= { exc1-Param-Input-IP-2-IGMP 1 }

exc1-Param-Input-IP-1-IGMP-Mode OBJECT-TYPE
	SYNTAX      INTEGER {exclude (0), include (1)}
	MAX-ACCESS  read-write
	STATUS      current
	DESCRIPTION
		""
        ::= { exc1-Param-Input-IP-1-IGMP 1 }

exc1-Param-Input-IP-2-RX-Reception-Mode OBJECT-TYPE
	SYNTAX      INTEGER {unicast (0), multicast (1)}
	MAX-ACCESS  read-write
	STATUS      current
	DESCRIPTION
		""
        ::= { exc1-Param-Input-IP-2-RX 1 }

exc1-Param-Input-IP-2-RX-IGMP-Version OBJECT-TYPE
	SYNTAX      INTEGER {ver2 (0), ver3 (1)}
	MAX-ACCESS  read-write
	STATUS      current
	DESCRIPTION
		""
        ::= { exc1-Param-Input-IP-2-RX 2 }

exc1-Param-Input-IP-2-RX-UDP-Port OBJECT-TYPE
	SYNTAX      Integer32
	MAX-ACCESS  read-write
	STATUS      current
	DESCRIPTION
		""
        ::= { exc1-Param-Input-IP-2-RX 3 }

exc1-Param-Input-IP-2-RX-UDP-Reception-Timeout OBJECT-TYPE
	SYNTAX      Integer32
	MAX-ACCESS  read-write
	STATUS      current
	DESCRIPTION
		""
        ::= { exc1-Param-Input-IP-2-RX 4 }

exc1-Param-Input-IP-2-RX-Multicast-Group-Address OBJECT-TYPE
	SYNTAX      IPAddress
	MAX-ACCESS  read-write
	STATUS      current
	DESCRIPTION
		""
        ::= { exc1-Param-Input-IP-2-RX 5 }

exc1-Param-Input-IP-2-RX-Receiver-Latency OBJECT-TYPE
	SYNTAX      Integer32
	MAX-ACCESS  read-write
	STATUS      current
	DESCRIPTION
		""
        ::= { exc1-Param-Input-IP-2-RX 6 }

exc1-Param-Input-IP-1-RX-Reception-Mode OBJECT-TYPE
	SYNTAX      INTEGER {unicast (0), multicast (1)}
	MAX-ACCESS  read-write
	STATUS      current
	DESCRIPTION
		""
        ::= { exc1-Param-Input-IP-1-RX 1 }

exc1-Param-Input-IP-1-RX-IGMP-Version OBJECT-TYPE
	SYNTAX      INTEGER {ver2 (0), ver3 (1)}
	MAX-ACCESS  read-write
	STATUS      current
	DESCRIPTION
		""
        ::= { exc1-Param-Input-IP-1-RX 2 }

exc1-Param-Input-IP-1-RX-UDP-Port OBJECT-TYPE
	SYNTAX      Integer32
	MAX-ACCESS  read-write
	STATUS      current
	DESCRIPTION
		""
        ::= { exc1-Param-Input-IP-1-RX 3 }

exc1-Param-Input-IP-1-RX-UDP-Reception-Timeout OBJECT-TYPE
	SYNTAX      Integer32
	MAX-ACCESS  read-write
	STATUS      current
	DESCRIPTION
		""
        ::= { exc1-Param-Input-IP-1-RX 4 }

exc1-Param-Input-IP-1-RX-Multicast-Group-Address OBJECT-TYPE
	SYNTAX      IPAddress
	MAX-ACCESS  read-write
	STATUS      current
	DESCRIPTION
		""
        ::= { exc1-Param-Input-IP-1-RX 5 }

exc1-Param-Input-IP-1-RX-Receiver-Latency OBJECT-TYPE
	SYNTAX      Integer32
	MAX-ACCESS  read-write
	STATUS      current
	DESCRIPTION
		""
        ::= { exc1-Param-Input-IP-1-RX 6 }

exc1-Param-Input-IP-2-DHCP OBJECT-TYPE
	SYNTAX      INTEGER {manually (0), dHCP (1)}
	MAX-ACCESS  read-only
	STATUS      current
	DESCRIPTION
		""
        ::= { exc1-Param-Input-IP-2-Control 1 }

exc1-Param-Input-IP-2-IP-Address OBJECT-TYPE
	SYNTAX      IPAddress
	MAX-ACCESS  read-write
	STATUS      current
	DESCRIPTION
		""
        ::= { exc1-Param-Input-IP-2-Control 2 }

exc1-Param-Input-IP-2-Subnet-Mask OBJECT-TYPE
	SYNTAX      IPAddress
	MAX-ACCESS  read-write
	STATUS      current
	DESCRIPTION
		""
        ::= { exc1-Param-Input-IP-2-Control 3 }

exc1-Param-Input-IP-2-Gateway OBJECT-TYPE
	SYNTAX      IPAddress
	MAX-ACCESS  read-write
	STATUS      current
	DESCRIPTION
		""
        ::= { exc1-Param-Input-IP-2-Control 4 }

exc1-Param-Input-IP-2-VLAN-ID OBJECT-TYPE
	SYNTAX      Integer32
	MAX-ACCESS  read-write
	STATUS      current
	DESCRIPTION
		""
        ::= { exc1-Param-Input-IP-2-Control 5 }

exc1-Param-Input-IP-2-Validate-Parameters OBJECT-TYPE
	SYNTAX      INTEGER {false(0), true(1)}
	MAX-ACCESS  read-write
	STATUS      current
	DESCRIPTION
		""
        ::= { exc1-Param-Input-IP-2-Control 6 }

exc1-Param-Input-IP-1-DHCP OBJECT-TYPE
	SYNTAX      INTEGER {manually (0), dHCP (1)}
	MAX-ACCESS  read-write
	STATUS      current
	DESCRIPTION
		""
        ::= { exc1-Param-Input-IP-1-Control 1 }

exc1-Param-Input-IP-1-IP-Address OBJECT-TYPE
	SYNTAX      IPAddress
	MAX-ACCESS  read-write
	STATUS      current
	DESCRIPTION
		""
        ::= { exc1-Param-Input-IP-1-Control 2 }

exc1-Param-Input-IP-1-Subnet-Mask OBJECT-TYPE
	SYNTAX      IPAddress
	MAX-ACCESS  read-write
	STATUS      current
	DESCRIPTION
		""
        ::= { exc1-Param-Input-IP-1-Control 3 }

exc1-Param-Input-IP-1-Gateway OBJECT-TYPE
	SYNTAX      IPAddress
	MAX-ACCESS  read-write
	STATUS      current
	DESCRIPTION
		""
        ::= { exc1-Param-Input-IP-1-Control 4 }

exc1-Param-Input-IP-1-VLAN-ID OBJECT-TYPE
	SYNTAX      Integer32
	MAX-ACCESS  read-write
	STATUS      current
	DESCRIPTION
		""
        ::= { exc1-Param-Input-IP-1-Control 5 }

exc1-Param-Input-IP-1-Validate-Parameters OBJECT-TYPE
	SYNTAX      INTEGER {false(0), true(1)}
	MAX-ACCESS  read-write
	STATUS      current
	DESCRIPTION
		""
        ::= { exc1-Param-Input-IP-1-Control 6 }

exc1-Param-Input-Clever-Switching OBJECT-TYPE
	SYNTAX      INTEGER {off (0), on (1)}
	MAX-ACCESS  read-write
	STATUS      current
	DESCRIPTION
		""
        ::= { exc1-Param-Input-Clever-Parameters 1 }

exc1-Param-Input-Clever-Auto-Switch-Back OBJECT-TYPE
	SYNTAX      INTEGER {off (0), on (1)}
	MAX-ACCESS  read-write
	STATUS      current
	DESCRIPTION
		""
        ::= { exc1-Param-Input-Clever-Parameters 2 }

exc1-Param-Input-Clever-Error-Threshold-Value OBJECT-TYPE
	SYNTAX      Integer32
	MAX-ACCESS  read-write
	STATUS      current
	DESCRIPTION
		""
        ::= { exc1-Param-Input-Clever-Parameters 3 }

exc1-Param-Input-Clever-Valid-Threshold-Value OBJECT-TYPE
	SYNTAX      Integer32
	MAX-ACCESS  read-write
	STATUS      current
	DESCRIPTION
		""
        ::= { exc1-Param-Input-Clever-Parameters 4 }

exc1-Param-Input-Main-TS-Source-Input-1 OBJECT-TYPE
	SYNTAX      INTEGER {off (0), aSI1 (1), aSI2 (2), iP (3), activeStream (5)}
	MAX-ACCESS  read-write
	STATUS      current
	DESCRIPTION
		""
        ::= { exc1-Param-Input-Main 1 }

exc1-Param-Input-Main-TS-Source-Input-2 OBJECT-TYPE
	SYNTAX      INTEGER {off (0), aSI1 (1), aSI2 (2), iP (3), activeStream (5)}
	MAX-ACCESS  read-write
	STATUS      current
	DESCRIPTION
		""
        ::= { exc1-Param-Input-Main 2 }

exc1-Param-Glonass-GPS-Control-Timestamp OBJECT-TYPE
	SYNTAX      INTEGER {gPS (1), gLONASS (2), uTC (3), uTC_SU (4)}
	MAX-ACCESS  read-write
	STATUS      current
	DESCRIPTION
		""
        ::= { exc1-Param-Glonass-GPS-Control 1 }

exc1-Param-Glonass-GPS-Control-Navigation-System OBJECT-TYPE
	SYNTAX      INTEGER {gPS_GLONASS (0), gPS (1), gLONASS (2), gPS_GLONASS_SBAS (10), gPS_SBAS (11), gLONASS_SBAS (12)}
	MAX-ACCESS  read-write
	STATUS      current
	DESCRIPTION
		""
        ::= { exc1-Param-Glonass-GPS-Control 2 }

exc1-Param-Glonass-GPS-Control-PPS-Delay OBJECT-TYPE
	SYNTAX      Integer32
	MAX-ACCESS  read-write
	STATUS      current
	DESCRIPTION
		""
        ::= { exc1-Param-Glonass-GPS-Control 3 }

exc1-Param-Glonass-GPS-Control-Receiver-Mode OBJECT-TYPE
	SYNTAX      INTEGER {navi (0), fixedCoordinates (1), averageCoordinates (2)}
	MAX-ACCESS  read-write
	STATUS      current
	DESCRIPTION
		""
        ::= { exc1-Param-Glonass-GPS-Control 4 }

exc1-Param-Glonass-GPS-Control-Coordinates-Averaging-Time OBJECT-TYPE
	SYNTAX      Integer32
	MAX-ACCESS  read-write
	STATUS      current
	DESCRIPTION
		""
        ::= { exc1-Param-Glonass-GPS-Control 5 }

exc1-Param-Glonass-GPS-Control-Minimal-SNR OBJECT-TYPE
	SYNTAX      Integer32
	MAX-ACCESS  read-write
	STATUS      current
	DESCRIPTION
		""
        ::= { exc1-Param-Glonass-GPS-Control 6 }

exc1-Param-Glonass-GPS-Monitoring-Module-Status-Normal OBJECT-TYPE
	SYNTAX      INTEGER {false(0), true(1)}
	MAX-ACCESS  read-only
	STATUS      current
	DESCRIPTION
		""
        ::= { exc1-Param-Glonass-GPS-Monitoring 1 }

exc1-Param-Glonass-GPS-Monitoring-Antenna-Status OBJECT-TYPE
	SYNTAX      INTEGER {normal (0), shortCircuit (1), noConnection (2)}
	MAX-ACCESS  read-only
	STATUS      current
	DESCRIPTION
		""
        ::= { exc1-Param-Glonass-GPS-Monitoring 2 }

exc1-Param-Glonass-GPS-Monitoring-Satellites-Lock OBJECT-TYPE
	SYNTAX      INTEGER {false(0), true(1)}
	MAX-ACCESS  read-only
	STATUS      current
	DESCRIPTION
		""
        ::= { exc1-Param-Glonass-GPS-Monitoring 3 }

exc1-Param-Glonass-GPS-Monitoring-PLL-Lock OBJECT-TYPE
	SYNTAX      INTEGER {false(0), true(1)}
	MAX-ACCESS  read-only
	STATUS      current
	DESCRIPTION
		""
        ::= { exc1-Param-Glonass-GPS-Monitoring 4 }

exc1-Param-Glonass-GPS-Monitoring-Mode OBJECT-TYPE
	SYNTAX      INTEGER {mode2D (0), mode3D (1)}
	MAX-ACCESS  read-only
	STATUS      current
	DESCRIPTION
		""
        ::= { exc1-Param-Glonass-GPS-Monitoring 5 }

exc1-Param-Glonass-GPS-Monitoring-Satellites-Number-GPS OBJECT-TYPE
	SYNTAX      Integer32
	MAX-ACCESS  read-only
	STATUS      current
	DESCRIPTION
		""
        ::= { exc1-Param-Glonass-GPS-Monitoring 6 }

exc1-Param-Glonass-GPS-Monitoring-Satellites-Number-GLONASS OBJECT-TYPE
	SYNTAX      Integer32
	MAX-ACCESS  read-only
	STATUS      current
	DESCRIPTION
		""
        ::= { exc1-Param-Glonass-GPS-Monitoring 7 }

exc1-Param-Glonass-GPS-Monitoring-Current-Time OBJECT-TYPE
	SYNTAX      OCTET STRING
	MAX-ACCESS  read-only
	STATUS      current
	DESCRIPTION
		""
        ::= { exc1-Param-Glonass-GPS-Monitoring 8 }

exc1-Param-Glonass-GPS-Monitoring-Current-Date OBJECT-TYPE
	SYNTAX      OCTET STRING
	MAX-ACCESS  read-only
	STATUS      current
	DESCRIPTION
		""
        ::= { exc1-Param-Glonass-GPS-Monitoring 9 }

exc1-Param-Glonass-GPS-Monitoring-Longitude OBJECT-TYPE
	SYNTAX      OCTET STRING
	MAX-ACCESS  read-only
	STATUS      current
	DESCRIPTION
		""
        ::= { exc1-Param-Glonass-GPS-Monitoring 10 }

exc1-Param-Glonass-GPS-Monitoring-Latitude OBJECT-TYPE
	SYNTAX      OCTET STRING
	MAX-ACCESS  read-only
	STATUS      current
	DESCRIPTION
		""
        ::= { exc1-Param-Glonass-GPS-Monitoring 11 }

exc1-Param-Glonass-GPS-Monitoring-Firmware-Version-Controller OBJECT-TYPE
	SYNTAX      OCTET STRING
	MAX-ACCESS  read-only
	STATUS      current
	DESCRIPTION
		""
        ::= { exc1-Param-Glonass-GPS-Monitoring 12 }

exc1-Param-Glonass-GPS-Monitoring-Firmware-Version-NAVIS OBJECT-TYPE
	SYNTAX      OCTET STRING
	MAX-ACCESS  read-only
	STATUS      current
	DESCRIPTION
		""
        ::= { exc1-Param-Glonass-GPS-Monitoring 13 }

exc1-Param-Ref-Lost-of-Reference-Signal-Timeout-Enable OBJECT-TYPE
	SYNTAX      INTEGER {false(0), true(1)}
	MAX-ACCESS  read-write
	STATUS      current
	DESCRIPTION
		""
        ::= { exc1-Param-Reference 1 }

exc1-Param-Ref-Lost-of-Reference-Signal-Timeout OBJECT-TYPE
	SYNTAX      Integer32
	MAX-ACCESS  read-write
	STATUS      current
	DESCRIPTION
		""
        ::= { exc1-Param-Reference 2 }

exc1-Param-Ref-PPS-Auto-Resync OBJECT-TYPE
	SYNTAX      INTEGER {false(0), true(1)}
	MAX-ACCESS  read-write
	STATUS      current
	DESCRIPTION
		""
        ::= { exc1-Param-Reference 3 }

exc1-Param-Ref-Reference-Source OBJECT-TYPE
	SYNTAX      INTEGER {internal10Mhz (0), external10Mhz (1), pPS (2)}
	MAX-ACCESS  read-write
	STATUS      current
	DESCRIPTION
		""
        ::= { exc1-Param-Reference 4 }

exc1-Param-Ref-PPS-Edge OBJECT-TYPE
	SYNTAX      INTEGER {rising (0), falling (1)}
	MAX-ACCESS  read-write
	STATUS      current
	DESCRIPTION
		""
        ::= { exc1-Param-Reference 5 }

exc1-Param-Ref-PPS-Source OBJECT-TYPE
	SYNTAX      INTEGER {embeddedGPS (0), external (1)}
	MAX-ACCESS  read-write
	STATUS      current
	DESCRIPTION
		""
        ::= { exc1-Param-Reference 6 }

exc1-Param-Ref-Backup-Clock-Source OBJECT-TYPE
	SYNTAX      INTEGER {internal10Mhz (0), external10Mhz (1), external1PPS (2)}
	MAX-ACCESS  read-write
	STATUS      current
	DESCRIPTION
		""
        ::= { exc1-Param-Reference 7 }

exc1-Param-Ref-PPS-Input-Output OBJECT-TYPE
	SYNTAX      INTEGER {input (0), output (1)}
	MAX-ACCESS  read-write
	STATUS      current
	DESCRIPTION
		""
        ::= { exc1-Param-Reference 8 }

exc1-Param-Mon-Clever-IP-Primary-Input-Status OBJECT-TYPE
	SYNTAX      INTEGER {ok (0), warning (1), failed (2)}
	MAX-ACCESS  read-only
	STATUS      current
	DESCRIPTION
		""
        ::= { exc1-Param-Mon-Clever-Switch-IP-Status 1 }

exc1-Param-Mon-Clever-IP-Secondary-Input-Status OBJECT-TYPE
	SYNTAX      INTEGER {ok (0), failed (1)}
	MAX-ACCESS  read-only
	STATUS      current
	DESCRIPTION
		""
        ::= { exc1-Param-Mon-Clever-Switch-IP-Status 2 }

exc1-Param-Mon-Clever-IP-Active-Stream OBJECT-TYPE
	SYNTAX      INTEGER {primaryInput (0), secondaryInput (1)}
	MAX-ACCESS  read-only
	STATUS      current
	DESCRIPTION
		""
        ::= { exc1-Param-Mon-Clever-Switch-IP-Status 3 }

exc1-Param-Mon-Clever-IP-RTP-Packet-Loss-Time OBJECT-TYPE
	SYNTAX      Integer32
	MAX-ACCESS  read-only
	STATUS      current
	DESCRIPTION
		""
        ::= { exc1-Param-Mon-Clever-Switch-IP-Status 4 }

exc1-Param-Mon-Clever-IP-RTP-Valid-Packet-Time OBJECT-TYPE
	SYNTAX      Integer32
	MAX-ACCESS  read-only
	STATUS      current
	DESCRIPTION
		""
        ::= { exc1-Param-Mon-Clever-Switch-IP-Status 5 }

exc1-Param-Mon-IP-2-RX-UDP-Reception-Active OBJECT-TYPE
	SYNTAX      INTEGER {false(0), true(1)}
	MAX-ACCESS  read-only
	STATUS      current
	DESCRIPTION
		""
        ::= { exc1-Param-Mon-IP-IP-2-RX-Status 1 }

exc1-Param-Mon-IP-2-RX-RTP-Locked OBJECT-TYPE
	SYNTAX      INTEGER {false(0), true(1)}
	MAX-ACCESS  read-only
	STATUS      current
	DESCRIPTION
		""
        ::= { exc1-Param-Mon-IP-IP-2-RX-Status 2 }

exc1-Param-Mon-IP-2-RX-High-Input-Bitrate OBJECT-TYPE
	SYNTAX      INTEGER {false(0), true(1)}
	MAX-ACCESS  read-only
	STATUS      current
	DESCRIPTION
		""
        ::= { exc1-Param-Mon-IP-IP-2-RX-Status 3 }

exc1-Param-Mon-IP-2-RX-Low-Latency OBJECT-TYPE
	SYNTAX      INTEGER {false(0), true(1)}
	MAX-ACCESS  read-only
	STATUS      current
	DESCRIPTION
		""
        ::= { exc1-Param-Mon-IP-IP-2-RX-Status 4 }

exc1-Param-Mon-IP-2-RX-FEC-Mode OBJECT-TYPE
	SYNTAX      INTEGER {none (0), fec1D (1), fec2D (2)}
	MAX-ACCESS  read-only
	STATUS      current
	DESCRIPTION
		""
        ::= { exc1-Param-Mon-IP-IP-2-RX-Status 5 }

exc1-Param-Mon-IP-2-RX-FEC-Columns-Number OBJECT-TYPE
	SYNTAX      Integer32
	MAX-ACCESS  read-only
	STATUS      current
	DESCRIPTION
		""
        ::= { exc1-Param-Mon-IP-IP-2-RX-Status 6 }

exc1-Param-Mon-IP-2-RX-FEC-Rows-Number OBJECT-TYPE
	SYNTAX      Integer32
	MAX-ACCESS  read-only
	STATUS      current
	DESCRIPTION
		""
        ::= { exc1-Param-Mon-IP-IP-2-RX-Status 7 }

exc1-Param-Mon-IP-2-RX-PER-before-FEC OBJECT-TYPE
	SYNTAX      Integer32
	MAX-ACCESS  read-only
	STATUS      current
	DESCRIPTION
		""
        ::= { exc1-Param-Mon-IP-IP-2-RX-Status 8 }

exc1-Param-Mon-IP-2-RX-Corrected-Packet-Counter OBJECT-TYPE
	SYNTAX      Integer32
	MAX-ACCESS  read-only
	STATUS      current
	DESCRIPTION
		""
        ::= { exc1-Param-Mon-IP-IP-2-RX-Status 9 }

exc1-Param-Mon-IP-2-RX-Uncorrected-Packet-Counter OBJECT-TYPE
	SYNTAX      Integer32
	MAX-ACCESS  read-only
	STATUS      current
	DESCRIPTION
		""
        ::= { exc1-Param-Mon-IP-IP-2-RX-Status 10 }

exc1-Param-Mon-IP-2-RX-Estimated-Latency OBJECT-TYPE
	SYNTAX      Integer32
	MAX-ACCESS  read-only
	STATUS      current
	DESCRIPTION
		""
        ::= { exc1-Param-Mon-IP-IP-2-RX-Status 11 }

exc1-Param-Mon-IP-1-RX-UDP-Reception-Active OBJECT-TYPE
	SYNTAX      INTEGER {false(0), true(1)}
	MAX-ACCESS  read-only
	STATUS      current
	DESCRIPTION
		""
        ::= { exc1-Param-Mon-IP-IP-1-RX-Status 1 }

exc1-Param-Mon-IP-1-RX-RTP-Locked OBJECT-TYPE
	SYNTAX      INTEGER {false(0), true(1)}
	MAX-ACCESS  read-only
	STATUS      current
	DESCRIPTION
		""
        ::= { exc1-Param-Mon-IP-IP-1-RX-Status 2 }

exc1-Param-Mon-IP-1-RX-High-Input-Bitrate OBJECT-TYPE
	SYNTAX      INTEGER {false(0), true(1)}
	MAX-ACCESS  read-only
	STATUS      current
	DESCRIPTION
		""
        ::= { exc1-Param-Mon-IP-IP-1-RX-Status 3 }

exc1-Param-Mon-IP-1-RX-Low-Latency OBJECT-TYPE
	SYNTAX      INTEGER {false(0), true(1)}
	MAX-ACCESS  read-only
	STATUS      current
	DESCRIPTION
		""
        ::= { exc1-Param-Mon-IP-IP-1-RX-Status 4 }

exc1-Param-Mon-IP-1-RX-FEC-Mode OBJECT-TYPE
	SYNTAX      INTEGER {none (0), fec1D (1), fec2D (2)}
	MAX-ACCESS  read-only
	STATUS      current
	DESCRIPTION
		""
        ::= { exc1-Param-Mon-IP-IP-1-RX-Status 5 }

exc1-Param-Mon-IP-1-RX-FEC-Columns-Number OBJECT-TYPE
	SYNTAX      Integer32
	MAX-ACCESS  read-only
	STATUS      current
	DESCRIPTION
		""
        ::= { exc1-Param-Mon-IP-IP-1-RX-Status 6 }

exc1-Param-Mon-IP-1-RX-FEC-Rows-Number OBJECT-TYPE
	SYNTAX      Integer32
	MAX-ACCESS  read-only
	STATUS      current
	DESCRIPTION
		""
        ::= { exc1-Param-Mon-IP-IP-1-RX-Status 7 }

exc1-Param-Mon-IP-1-RX-PER-before-FEC OBJECT-TYPE
	SYNTAX      Integer32
	MAX-ACCESS  read-only
	STATUS      current
	DESCRIPTION
		""
        ::= { exc1-Param-Mon-IP-IP-1-RX-Status 8 }

exc1-Param-Mon-IP-1-RX-Corrected-Packet-Counter OBJECT-TYPE
	SYNTAX      Integer32
	MAX-ACCESS  read-only
	STATUS      current
	DESCRIPTION
		""
        ::= { exc1-Param-Mon-IP-IP-1-RX-Status 9 }

exc1-Param-Mon-IP-1-RX-Uncorrected-Packet-Counter OBJECT-TYPE
	SYNTAX      Integer32
	MAX-ACCESS  read-only
	STATUS      current
	DESCRIPTION
		""
        ::= { exc1-Param-Mon-IP-IP-1-RX-Status 10 }

exc1-Param-Mon-IP-1-RX-Estimated-Latency OBJECT-TYPE
	SYNTAX      Integer32
	MAX-ACCESS  read-only
	STATUS      current
	DESCRIPTION
		""
        ::= { exc1-Param-Mon-IP-IP-1-RX-Status 11 }

exc1-Param-Mon-IP-2-Link-Status OBJECT-TYPE
	SYNTAX      INTEGER {linkDown (0), eth10Full (1), eth10Half (2), eth100Full (3), eth100Half (4), eth1000Full (5), eth1000Half (6)}
	MAX-ACCESS  read-only
	STATUS      current
	DESCRIPTION
		""
        ::= { exc1-Param-Mon-IP-IP-2-Status 1 }

exc1-Param-Mon-IP-2-Received-Packet-Counter OBJECT-TYPE
	SYNTAX      Integer32
	MAX-ACCESS  read-only
	STATUS      current
	DESCRIPTION
		""
        ::= { exc1-Param-Mon-IP-IP-2-Status 2 }

exc1-Param-Mon-IP-2-Transmitted-Packet-Counter OBJECT-TYPE
	SYNTAX      Integer32
	MAX-ACCESS  read-only
	STATUS      current
	DESCRIPTION
		""
        ::= { exc1-Param-Mon-IP-IP-2-Status 3 }

exc1-Param-Mon-IP-2-Ethernet-CRC-Error-Counter OBJECT-TYPE
	SYNTAX      Integer32
	MAX-ACCESS  read-only
	STATUS      current
	DESCRIPTION
		""
        ::= { exc1-Param-Mon-IP-IP-2-Status 4 }

exc1-Param-Mon-IP-1-Link-Status OBJECT-TYPE
	SYNTAX      INTEGER {linkDown (0), eth10Full (1), eth10Half (2), eth100Full (3), eth100Half (4), eth1000Full (5), eth1000Half (6)}
	MAX-ACCESS  read-only
	STATUS      current
	DESCRIPTION
		""
        ::= { exc1-Param-Mon-IP-IP-1-Status 1 }

exc1-Param-Mon-IP-1-Received-Packet-Counter OBJECT-TYPE
	SYNTAX      Integer32
	MAX-ACCESS  read-only
	STATUS      current
	DESCRIPTION
		""
        ::= { exc1-Param-Mon-IP-IP-1-Status 2 }

exc1-Param-Mon-IP-1-Transmitted-Packet-Counter OBJECT-TYPE
	SYNTAX      Integer32
	MAX-ACCESS  read-only
	STATUS      current
	DESCRIPTION
		""
        ::= { exc1-Param-Mon-IP-IP-1-Status 3 }

exc1-Param-Mon-IP-1-Ethernet-CRC-Error-Counter OBJECT-TYPE
	SYNTAX      Integer32
	MAX-ACCESS  read-only
	STATUS      current
	DESCRIPTION
		""
        ::= { exc1-Param-Mon-IP-IP-1-Status 4 }

exc1-Param-Mon-IP-Input-Signal-Detected OBJECT-TYPE
	SYNTAX      INTEGER {false(0), true(1)}
	MAX-ACCESS  read-only
	STATUS      current
	DESCRIPTION
		""
        ::= { exc1-Param-Mon-IP-Input-Status 1 }

exc1-Param-Mon-IP-Input-Synchronization-Lost OBJECT-TYPE
	SYNTAX      INTEGER {false(0), true(1)}
	MAX-ACCESS  read-only
	STATUS      current
	DESCRIPTION
		""
        ::= { exc1-Param-Mon-IP-Input-Status 2 }

exc1-Param-Mon-IP-Input-ISK-Char-Error OBJECT-TYPE
	SYNTAX      INTEGER {false(0), true(1)}
	MAX-ACCESS  read-only
	STATUS      current
	DESCRIPTION
		""
        ::= { exc1-Param-Mon-IP-Input-Status 3 }

exc1-Param-Mon-IP-Input-MPEG-TS-Packet-Length OBJECT-TYPE
	SYNTAX      INTEGER {false(0), true(1)}
	MAX-ACCESS  read-only
	STATUS      current
	DESCRIPTION
		""
        ::= { exc1-Param-Mon-IP-Input-Status 4 }

exc1-Param-Mon-IP-Input-FEC-Detected OBJECT-TYPE
	SYNTAX      INTEGER {false(0), true(1)}
	MAX-ACCESS  read-only
	STATUS      current
	DESCRIPTION
		""
        ::= { exc1-Param-Mon-IP-Input-Status 5 }

exc1-Param-Mon-IP-Input-Total-Bitrate OBJECT-TYPE
	SYNTAX      Integer32
	MAX-ACCESS  read-only
	STATUS      current
	DESCRIPTION
		""
        ::= { exc1-Param-Mon-IP-Input-Status 6 }

exc1-Param-Mon-ASI-2-Signal-Detected OBJECT-TYPE
	SYNTAX      INTEGER {false(0), true(1)}
	MAX-ACCESS  read-only
	STATUS      current
	DESCRIPTION
		""
        ::= { exc1-Param-Mon-ASI-2-Status 1 }

exc1-Param-Mon-ASI-2-Synchronization-Lost OBJECT-TYPE
	SYNTAX      INTEGER {false(0), true(1)}
	MAX-ACCESS  read-only
	STATUS      current
	DESCRIPTION
		""
        ::= { exc1-Param-Mon-ASI-2-Status 2 }

exc1-Param-Mon-ASI-2-ISK-Char-Error OBJECT-TYPE
	SYNTAX      INTEGER {false(0), true(1)}
	MAX-ACCESS  read-only
	STATUS      current
	DESCRIPTION
		""
        ::= { exc1-Param-Mon-ASI-2-Status 3 }

exc1-Param-Mon-ASI-2-MPEG-TS-Packet-Length OBJECT-TYPE
	SYNTAX      INTEGER {false(0), true(1)}
	MAX-ACCESS  read-only
	STATUS      current
	DESCRIPTION
		""
        ::= { exc1-Param-Mon-ASI-2-Status 4 }

exc1-Param-Mon-ASI-2-FEC-Detected OBJECT-TYPE
	SYNTAX      INTEGER {false(0), true(1)}
	MAX-ACCESS  read-only
	STATUS      current
	DESCRIPTION
		""
        ::= { exc1-Param-Mon-ASI-2-Status 5 }

exc1-Param-Mon-ASI-2-Total-Bitrate OBJECT-TYPE
	SYNTAX      Integer32
	MAX-ACCESS  read-only
	STATUS      current
	DESCRIPTION
		""
        ::= { exc1-Param-Mon-ASI-2-Status 6 }

exc1-Param-Mon-ASI-1-Signal-Detected OBJECT-TYPE
	SYNTAX      INTEGER {false(0), true(1)}
	MAX-ACCESS  read-only
	STATUS      current
	DESCRIPTION
		""
        ::= { exc1-Param-Mon-ASI-1-Status 1 }

exc1-Param-Mon-ASI-1-Synchronization-Lost OBJECT-TYPE
	SYNTAX      INTEGER {false(0), true(1)}
	MAX-ACCESS  read-only
	STATUS      current
	DESCRIPTION
		""
        ::= { exc1-Param-Mon-ASI-1-Status 2 }

exc1-Param-Mon-ASI-1-ISK-Char-Error OBJECT-TYPE
	SYNTAX      INTEGER {false(0), true(1)}
	MAX-ACCESS  read-only
	STATUS      current
	DESCRIPTION
		""
        ::= { exc1-Param-Mon-ASI-1-Status 3 }

exc1-Param-Mon-ASI-1-MPEG-TS-Packet-Length OBJECT-TYPE
	SYNTAX      INTEGER {false(0), true(1)}
	MAX-ACCESS  read-only
	STATUS      current
	DESCRIPTION
		""
        ::= { exc1-Param-Mon-ASI-1-Status 4 }

exc1-Param-Mon-ASI-1-FEC-Detected OBJECT-TYPE
	SYNTAX      INTEGER {false(0), true(1)}
	MAX-ACCESS  read-only
	STATUS      current
	DESCRIPTION
		""
        ::= { exc1-Param-Mon-ASI-1-Status 5 }

exc1-Param-Mon-ASI-1-Total-Bitrate OBJECT-TYPE
	SYNTAX      Integer32
	MAX-ACCESS  read-only
	STATUS      current
	DESCRIPTION
		""
        ::= { exc1-Param-Mon-ASI-1-Status 6 }

exc1-Param-Mon-Clever-Input-1-Status OBJECT-TYPE
	SYNTAX      INTEGER {ok (0), fail (1)}
	MAX-ACCESS  read-only
	STATUS      current
	DESCRIPTION
		""
        ::= { exc1-Param-Mon-Clever-Status 1 }

exc1-Param-Mon-Clever-Error-Counter OBJECT-TYPE
	SYNTAX      Unsigned32
	MAX-ACCESS  read-only
	STATUS      current
	DESCRIPTION
		""
        ::= { exc1-Param-Mon-Clever-Status 2 }

exc1-Param-Mon-Clever-Valid-Counter OBJECT-TYPE
	SYNTAX      Unsigned32
	MAX-ACCESS  read-only
	STATUS      current
	DESCRIPTION
		""
        ::= { exc1-Param-Mon-Clever-Status 3 }

exc1-Param-Mon-Stream2-Network-Delay OBJECT-TYPE
	SYNTAX      Integer32
	MAX-ACCESS  read-only
	STATUS      current
	DESCRIPTION
		""
        ::= { exc1-Param-Mon-Stream2 1 }

exc1-Param-Mon-Stream2-Max-Network-Delay OBJECT-TYPE
	SYNTAX      Integer32
	MAX-ACCESS  read-only
	STATUS      current
	DESCRIPTION
		""
        ::= { exc1-Param-Mon-Stream2 2 }

exc1-Param-Mon-Stream2-Average-Total-Bitrate OBJECT-TYPE
	SYNTAX      Integer32
	MAX-ACCESS  read-only
	STATUS      current
	DESCRIPTION
		""
        ::= { exc1-Param-Mon-Stream2 3 }

exc1-Param-Mon-Stream2-Average-Useful-Bitrate OBJECT-TYPE
	SYNTAX      Integer32
	MAX-ACCESS  read-only
	STATUS      current
	DESCRIPTION
		""
        ::= { exc1-Param-Mon-Stream2 4 }

exc1-Param-Mon-Stream1-Network-Delay OBJECT-TYPE
	SYNTAX      Integer32
	MAX-ACCESS  read-only
	STATUS      current
	DESCRIPTION
		""
        ::= { exc1-Param-Mon-Stream1 1 }

exc1-Param-Mon-Stream1-Max-Network-Delay OBJECT-TYPE
	SYNTAX      Integer32
	MAX-ACCESS  read-only
	STATUS      current
	DESCRIPTION
		""
        ::= { exc1-Param-Mon-Stream1 2 }

exc1-Param-Mon-Stream1-Average-Total-Bitrate OBJECT-TYPE
	SYNTAX      Integer32
	MAX-ACCESS  read-only
	STATUS      current
	DESCRIPTION
		""
        ::= { exc1-Param-Mon-Stream1 3 }

exc1-Param-Mon-Stream1-Average-Useful-Bitrate OBJECT-TYPE
	SYNTAX      Integer32
	MAX-ACCESS  read-only
	STATUS      current
	DESCRIPTION
		""
        ::= { exc1-Param-Mon-Stream1 4 }

exc1-Param-Mon-Main-Exciter-Power-Output OBJECT-TYPE
	SYNTAX      Integer32
	MAX-ACCESS  read-only
	STATUS      current
	DESCRIPTION
		""
        ::= { exc1-Param-Mon-Main 1 }

exc1-Param-Mon-Main-Standard OBJECT-TYPE
	SYNTAX      INTEGER {dVBTH (0), dVBT2 (4)}
	MAX-ACCESS  read-only
	STATUS      current
	DESCRIPTION
		""
        ::= { exc1-Param-Mon-Main 2 }

exc1-Param-Mon-Main-Selected-Reference OBJECT-TYPE
	SYNTAX      INTEGER {internal (0), external10Mhz (1), external1PPS (2)}
	MAX-ACCESS  read-only
	STATUS      current
	DESCRIPTION
		""
        ::= { exc1-Param-Mon-Main 3 }

exc1-Param-Mon-Main-Mute-Source OBJECT-TYPE
	SYNTAX      INTEGER {muteOff (0), muteOnLicenseFail (1), muteOnInitInProgress (2), muteOnUserRequest (3), muteOnStartingDelay (4), muteOnTsStreamError (5), muteOnReferenceError (6), muteOnHardwareError (7), muteOnFirmwareUpgrade (8), muteOnWarmUp (9), muteOnSettingsErrors (255)}
	MAX-ACCESS  read-only
	STATUS      current
	DESCRIPTION
		""
        ::= { exc1-Param-Mon-Main 4 }

exc1-Param-Mon-Main-RF-Frequency OBJECT-TYPE
	SYNTAX      Integer32
	MAX-ACCESS  read-only
	STATUS      current
	DESCRIPTION
		""
        ::= { exc1-Param-Mon-Main 5 }

exc1-Param-Mon-Main-TV-Channel OBJECT-TYPE
	SYNTAX      Integer32
	MAX-ACCESS  read-only
	STATUS      current
	DESCRIPTION
		""
        ::= { exc1-Param-Mon-Main 6 }

exc1-Param-Mon-Main-Selected-Input OBJECT-TYPE
	SYNTAX      INTEGER {stream1 (0), stream2 (1)}
	MAX-ACCESS  read-only
	STATUS      current
	DESCRIPTION
		""
        ::= { exc1-Param-Mon-Main 7 }

exc1-Param-Mon-Main-Temperature OBJECT-TYPE
	SYNTAX      Integer32
	MAX-ACCESS  read-only
	STATUS      current
	DESCRIPTION
		""
        ::= { exc1-Param-Mon-Main 8 }

exc1-Param-Mon-Main-Average-Useful-Stream-Bitrate OBJECT-TYPE
	SYNTAX      Integer32
	MAX-ACCESS  read-only
	STATUS      current
	DESCRIPTION
		""
        ::= { exc1-Param-Mon-Main 9 }

exc1-Param-Mon-Main-Time-Margin-Stream-1 OBJECT-TYPE
	SYNTAX      Integer32
	MAX-ACCESS  read-only
	STATUS      current
	DESCRIPTION
		""
        ::= { exc1-Param-Mon-Main 10 }

exc1-Param-Mon-Main-Time-Margin-Stream-2 OBJECT-TYPE
	SYNTAX      Integer32
	MAX-ACCESS  read-only
	STATUS      current
	DESCRIPTION
		""
        ::= { exc1-Param-Mon-Main 11 }

exc1-DisplayMain-Status-Info OBJECT-TYPE
	SYNTAX      OCTET STRING
	MAX-ACCESS  read-only
	STATUS      current
	DESCRIPTION
		""
        ::= { exc1-Display-Main 1 }

exc1-DisplayMain-Status-Warning OBJECT-TYPE
	SYNTAX      OCTET STRING
	MAX-ACCESS  read-only
	STATUS      current
	DESCRIPTION
		""
        ::= { exc1-Display-Main 2 }

exc1-DisplayMain-Status-Failure OBJECT-TYPE
	SYNTAX      OCTET STRING
	MAX-ACCESS  read-only
	STATUS      current
	DESCRIPTION
		""
        ::= { exc1-Display-Main 3 }

exc1-Aux-Cmd-Is-Get-Exciter-Power-Out OBJECT-TYPE
	SYNTAX      INTEGER {false(0), true(1)}
	MAX-ACCESS  read-only
	STATUS      current
	DESCRIPTION
		""
        ::= { exc1-Aux-Commands 1 }

exc1-Aux-Cmd-Is-Get-DVB-T2-Time-Margin OBJECT-TYPE
	SYNTAX      INTEGER {false(0), true(1)}
	MAX-ACCESS  read-only
	STATUS      current
	DESCRIPTION
		""
        ::= { exc1-Aux-Commands 2 }

exc1-Aux-Cmd-Is-Set-IP-Network-Iface-Cfg-Opt OBJECT-TYPE
	SYNTAX      INTEGER {false(0), true(1)}
	MAX-ACCESS  read-only
	STATUS      current
	DESCRIPTION
		""
        ::= { exc1-Aux-Commands 3 }

exc1-Aux-Cmd-Is-Get-Navis-Firmware-Version OBJECT-TYPE
	SYNTAX      INTEGER {false(0), true(1)}
	MAX-ACCESS  read-only
	STATUS      current
	DESCRIPTION
		""
        ::= { exc1-Aux-Commands 4 }

exc1-Aux-Cmd-Is-Get-Minimal-SNR OBJECT-TYPE
	SYNTAX      INTEGER {false(0), true(1)}
	MAX-ACCESS  read-only
	STATUS      current
	DESCRIPTION
		""
        ::= { exc1-Aux-Commands 5 }

exc1-Aux-Opt-Is-TS-Over-IP OBJECT-TYPE
	SYNTAX      INTEGER {false(0), true(1)}
	MAX-ACCESS  read-only
	STATUS      current
	DESCRIPTION
		""
        ::= { exc1-Aux-Options 1 }

exc1-Aux-Opt-Is-GPS OBJECT-TYPE
	SYNTAX      INTEGER {false(0), true(1)}
	MAX-ACCESS  read-only
	STATUS      current
	DESCRIPTION
		""
        ::= { exc1-Aux-Options 2 }

exc1-Aux-Opt-Is-G4C OBJECT-TYPE
	SYNTAX      INTEGER {false(0), true(1)}
	MAX-ACCESS  read-only
	STATUS      current
	DESCRIPTION
		""
        ::= { exc1-Aux-Options 3 }

exc1-Aux-Opt-Is-New-FTP OBJECT-TYPE
	SYNTAX      INTEGER {false(0), true(1)}
	MAX-ACCESS  read-only
	STATUS      current
	DESCRIPTION
		""
        ::= { exc1-Aux-Options 4 }

exc1-Aux-Values-Correct-Pilot-Patterns OBJECT-TYPE
	SYNTAX      Integer32
	MAX-ACCESS  read-only
	STATUS      current
	DESCRIPTION
		""
        ::= { exc1-Aux-Values 1 }

exc1-Aux-Values-Correct-Guard-Intervals OBJECT-TYPE
	SYNTAX      Integer32
	MAX-ACCESS  read-only
	STATUS      current
	DESCRIPTION
		""
        ::= { exc1-Aux-Values 2 }

exc1-Aux-Process-Is-Standard-Changing OBJECT-TYPE
	SYNTAX      INTEGER {false(0), true(1)}
	MAX-ACCESS  read-only
	STATUS      current
	DESCRIPTION
		""
        ::= { exc1-Aux-Processing 1 }

exc1-Aux-Process-Is-MT2-Rebooting OBJECT-TYPE
	SYNTAX      INTEGER {false(0), true(1)}
	MAX-ACCESS  read-only
	STATUS      current
	DESCRIPTION
		""
        ::= { exc1-Aux-Processing 2 }

exc1-Aux-Process-Is-MT2-Firmware-Updating OBJECT-TYPE
	SYNTAX      INTEGER {false(0), true(1)}
	MAX-ACCESS  read-only
	STATUS      current
	DESCRIPTION
		""
        ::= { exc1-Aux-Processing 3 }

exc1-Aux-Process-Is-Controller-Rebooting OBJECT-TYPE
	SYNTAX      INTEGER {false(0), true(1)}
	MAX-ACCESS  read-only
	STATUS      current
	DESCRIPTION
		""
        ::= { exc1-Aux-Processing 4 }

exc1-Aux-Connected-Is-Connected-DVBT2-Module OBJECT-TYPE
	SYNTAX      INTEGER {false(0), true(1)}
	MAX-ACCESS  read-only
	STATUS      current
	DESCRIPTION
		""
        ::= { exc1-Aux-Connected 1 }

exc1-Aux-Connected-Is-Connected-Glonass-Module OBJECT-TYPE
	SYNTAX      INTEGER {false(0), true(1)}
	MAX-ACCESS  read-only
	STATUS      current
	DESCRIPTION
		""
        ::= { exc1-Aux-Connected 2 }

exc1-Unit-Connected OBJECT-TYPE
	SYNTAX      INTEGER {false(0), true(1)}
	MAX-ACCESS  read-only
	STATUS      current
	DESCRIPTION
		""
        ::= { exc1-Unit 1 }

exc1-Unit-Warning   OBJECT-TYPE
	SYNTAX      INTEGER {false(0), true(1)}
	MAX-ACCESS  read-only
	STATUS      current
	DESCRIPTION
		""
        ::= { exc1-Unit 2 }

exc1-Unit-Failure   OBJECT-TYPE
	SYNTAX      INTEGER {false(0), true(1)}
	MAX-ACCESS  read-only
	STATUS      current
	DESCRIPTION
		""
        ::= { exc1-Unit 3 }

exc1-Unit-Busy      OBJECT-TYPE
	SYNTAX      Integer32
	MAX-ACCESS  read-only
	STATUS      current
	DESCRIPTION
		""
        ::= { exc1-Unit 4 }

exc1-Unit-Model     OBJECT-TYPE
	SYNTAX      OCTET STRING
	MAX-ACCESS  read-only
	STATUS      current
	DESCRIPTION
		""
        ::= { exc1-Unit 5 }

exc1-Unit-Serial-Number OBJECT-TYPE
	SYNTAX      Integer32
	MAX-ACCESS  read-only
	STATUS      current
	DESCRIPTION
		""
        ::= { exc1-Unit 6 }

exc1-Unit-Firmware-Version OBJECT-TYPE
	SYNTAX      OCTET STRING
	MAX-ACCESS  read-only
	STATUS      current
	DESCRIPTION
		""
        ::= { exc1-Unit 7 }

exc1-Unit-Uptime    OBJECT-TYPE
	SYNTAX      DateAndTime
	MAX-ACCESS  read-only
	STATUS      current
	DESCRIPTION
		"<unused>"
        ::= { exc1-Unit 8 }

exc1-Unit-Post-Writes-Count OBJECT-TYPE
	SYNTAX      Integer32
	MAX-ACCESS  read-only
	STATUS      current
	DESCRIPTION
		"<unused>"
        ::= { exc1-Unit 9 }

exc1-Unit-IP-Address OBJECT-TYPE
	SYNTAX      IPAddress
	MAX-ACCESS  read-only
	STATUS      current
	DESCRIPTION
		""
        ::= { exc1-Unit 10 }

exc1-Unit-TCP-Port  OBJECT-TYPE
	SYNTAX      Integer32
	MAX-ACCESS  read-only
	STATUS      current
	DESCRIPTION
		""
        ::= { exc1-Unit 11 }

exc1-Unit-Adapter   OBJECT-TYPE
	SYNTAX      OCTET STRING
	MAX-ACCESS  read-only
	STATUS      current
	DESCRIPTION
		"<unused>"
        ::= { exc1-Unit 12 }

exc1-Unit-Reconnects OBJECT-TYPE
	SYNTAX      Integer32
	MAX-ACCESS  read-only
	STATUS      current
	DESCRIPTION
		""
        ::= { exc1-Unit 13 }

ctl1cu6Cu6Msg-Status-Info OBJECT-TYPE
	SYNTAX      OCTET STRING
	MAX-ACCESS  read-only
	STATUS      current
	DESCRIPTION
		""
        ::= { ctl1cu6-Cu6Messages 1 }

ctl1cu6Cu6Msg-Status-Warning OBJECT-TYPE
	SYNTAX      OCTET STRING
	MAX-ACCESS  read-only
	STATUS      current
	DESCRIPTION
		""
        ::= { ctl1cu6-Cu6Messages 2 }

ctl1cu6Cu6Msg-Status-Failure OBJECT-TYPE
	SYNTAX      OCTET STRING
	MAX-ACCESS  read-only
	STATUS      current
	DESCRIPTION
		""
        ::= { ctl1cu6-Cu6Messages 3 }

ctl1cu6Cu6CtlReset  OBJECT-TYPE
	SYNTAX      Integer32
	MAX-ACCESS  read-write
	STATUS      current
	DESCRIPTION
		""
        ::= { ctl1cu6-Cu6Control 1 }

ctl1cu6Cu6CtlModel  OBJECT-TYPE
	SYNTAX      INTEGER {none (0), triView (1), trinity (2), ssm (3)}
	MAX-ACCESS  read-write
	STATUS      current
	DESCRIPTION
		""
        ::= { ctl1cu6-Cu6Control 3 }

ctl1cu6Cu6DispHardwareVersion OBJECT-TYPE
	SYNTAX      OCTET STRING
	MAX-ACCESS  read-only
	STATUS      current
	DESCRIPTION
		""
        ::= { ctl1cu6-Cu6Display 1 }

ctl1cu6Cu6DispSoftwareVersion OBJECT-TYPE
	SYNTAX      OCTET STRING
	MAX-ACCESS  read-only
	STATUS      current
	DESCRIPTION
		""
        ::= { ctl1cu6-Cu6Display 2 }

ctl1cu6Cu6DispMode  OBJECT-TYPE
	SYNTAX      INTEGER {controlUnit (0), ssm (1), ballast (2)}
	MAX-ACCESS  read-only
	STATUS      current
	DESCRIPTION
		""
        ::= { ctl1cu6-Cu6Display 3 }

ctl1cu6Cu6DispSwitchSpareLedColor OBJECT-TYPE
	SYNTAX      INTEGER {green (0), red (1)}
	MAX-ACCESS  read-only
	STATUS      current
	DESCRIPTION
		""
        ::= { ctl1cu6-Cu6Display 4 }

ctl1cu6Cu6DispSwitchSpareLedStatus OBJECT-TYPE
	SYNTAX      INTEGER {light (0), blink (1)}
	MAX-ACCESS  read-only
	STATUS      current
	DESCRIPTION
		""
        ::= { ctl1cu6-Cu6Display 5 }

ctl1cu6Cu6DispMuteState OBJECT-TYPE
	SYNTAX      INTEGER {unMuted (0), muted (1)}
	MAX-ACCESS  read-only
	STATUS      current
	DESCRIPTION
		""
        ::= { ctl1cu6-Cu6Display 6 }

ctl1BalBallastPower1 OBJECT-TYPE
	SYNTAX      Integer32
	MAX-ACCESS  read-only
	STATUS      current
	DESCRIPTION
		"P1+2 ,%"
        ::= { ctl1-Ballast 1 }

ctl1BalBallastPower2 OBJECT-TYPE
	SYNTAX      Integer32
	MAX-ACCESS  read-only
	STATUS      current
	DESCRIPTION
		"P3+4 ,%"
        ::= { ctl1-Ballast 2 }

ctl1BalBallastPower3 OBJECT-TYPE
	SYNTAX      Integer32
	MAX-ACCESS  read-only
	STATUS      current
	DESCRIPTION
		"P1,2+3,4 ,%"
        ::= { ctl1-Ballast 3 }

ctl1BalBallastPower4 OBJECT-TYPE
	SYNTAX      Integer32
	MAX-ACCESS  read-only
	STATUS      current
	DESCRIPTION
		"P5+6 ,%"
        ::= { ctl1-Ballast 4 }

ctl1BalBallastPower5 OBJECT-TYPE
	SYNTAX      Integer32
	MAX-ACCESS  read-only
	STATUS      current
	DESCRIPTION
		"P7+8 ,%"
        ::= { ctl1-Ballast 5 }

ctl1BalBallastPower6 OBJECT-TYPE
	SYNTAX      Integer32
	MAX-ACCESS  read-only
	STATUS      current
	DESCRIPTION
		"P5,6+7,8 ,%"
        ::= { ctl1-Ballast 6 }

ctl1BalBallastPower7 OBJECT-TYPE
	SYNTAX      Integer32
	MAX-ACCESS  read-only
	STATUS      current
	DESCRIPTION
		"P1..4+5..8 ,%"
        ::= { ctl1-Ballast 7 }

ctl1Ctl-Active-Exciter OBJECT-TYPE
	SYNTAX      INTEGER {nA (0), exciter_1 (1), exciter_2 (2)}
	MAX-ACCESS  read-only
	STATUS      current
	DESCRIPTION
		""
        ::= { ctl1-Controls 1 }

ctl1Ctl-Auto-Switching OBJECT-TYPE
	SYNTAX      INTEGER {off (0), on (1), unused (-1)}
	MAX-ACCESS  read-write
	STATUS      current
	DESCRIPTION
		"GET: 0, 1, -1 
 SET: 0, 1"
        ::= { ctl1-Controls 2 }

ctl1Ctl-ASI-Mode    OBJECT-TYPE
	SYNTAX      INTEGER {nA (0), activeExciter (1), bothExciters (2)}
	MAX-ACCESS  read-write
	STATUS      current
	DESCRIPTION
		""
        ::= { ctl1-Controls 3 }

ctl1Disp-Power-Out-Value OBJECT-TYPE
	SYNTAX      Integer32
	MAX-ACCESS  read-only
	STATUS      current
	DESCRIPTION
		""
        ::= { ctl1-Display 1 }

ctl1Disp-Power-Out-Divider OBJECT-TYPE
	SYNTAX      Integer32
	MAX-ACCESS  read-only
	STATUS      current
	DESCRIPTION
		""
        ::= { ctl1-Display 2 }

ctl1Disp-Power-Out-Units OBJECT-TYPE
	SYNTAX      INTEGER {notAvailable (0), watt (1), kiloWatt (2), db (3), percent (4)}
	MAX-ACCESS  read-only
	STATUS      current
	DESCRIPTION
		""
        ::= { ctl1-Display 3 }

ctl1Disp-Power-Ref-Value OBJECT-TYPE
	SYNTAX      Integer32
	MAX-ACCESS  read-only
	STATUS      current
	DESCRIPTION
		""
        ::= { ctl1-Display 4 }

ctl1Disp-Power-Ref-Divider OBJECT-TYPE
	SYNTAX      Integer32
	MAX-ACCESS  read-only
	STATUS      current
	DESCRIPTION
		""
        ::= { ctl1-Display 5 }

ctl1Disp-Power-Ref-Units OBJECT-TYPE
	SYNTAX      INTEGER {notAvailable (0), watt (1), kiloWatt (2), db (3), percent (4)}
	MAX-ACCESS  read-only
	STATUS      current
	DESCRIPTION
		""
        ::= { ctl1-Display 6 }

ctl1Disp-Power-Bal-Value OBJECT-TYPE
	SYNTAX      Integer32
	MAX-ACCESS  read-only
	STATUS      current
	DESCRIPTION
		""
        ::= { ctl1-Display 7 }

ctl1Disp-Power-Bal-Divider OBJECT-TYPE
	SYNTAX      Integer32
	MAX-ACCESS  read-only
	STATUS      current
	DESCRIPTION
		""
        ::= { ctl1-Display 8 }

ctl1Disp-Power-Bal-Units OBJECT-TYPE
	SYNTAX      INTEGER {notAvailable (0), watt (1), kiloWatt (2), db (3), percent (4), unused (-1)}
	MAX-ACCESS  read-only
	STATUS      current
	DESCRIPTION
		""
        ::= { ctl1-Display 9 }

ctl1Disp-SWR        OBJECT-TYPE
	SYNTAX      Integer32
	MAX-ACCESS  read-only
	STATUS      current
	DESCRIPTION
		""
        ::= { ctl1-Display 10 }

ctl1Disp-SWR-Divider OBJECT-TYPE
	SYNTAX      Integer32
	MAX-ACCESS  read-only
	STATUS      current
	DESCRIPTION
		""
        ::= { ctl1-Display 11 }

ctl1Disp-SWR-Units  OBJECT-TYPE
	SYNTAX      Integer32
	MAX-ACCESS  read-only
	STATUS      current
	DESCRIPTION
		""
        ::= { ctl1-Display 12 }

ctl1Disp-Exciter-1-Status OBJECT-TYPE
	SYNTAX      INTEGER {unused (0), notReady (1), ready (2), noAgent (3)}
	MAX-ACCESS  read-only
	STATUS      current
	DESCRIPTION
		""
        ::= { ctl1-Display 13 }

ctl1Disp-Exciter-2-Status OBJECT-TYPE
	SYNTAX      INTEGER {unused (0), notReady (1), ready (2), noAgent (3)}
	MAX-ACCESS  read-only
	STATUS      current
	DESCRIPTION
		""
        ::= { ctl1-Display 14 }

ctl1Aux-Exciter-Select-State OBJECT-TYPE
	SYNTAX      INTEGER {disabled (0), enabled (1)}
	MAX-ACCESS  read-only
	STATUS      current
	DESCRIPTION
		""
        ::= { ctl1-Auxiliary 1 }

ctl1Aux-Ballast-Powers-Count OBJECT-TYPE
	SYNTAX      Integer32
	MAX-ACCESS  read-only
	STATUS      current
	DESCRIPTION
		""
        ::= { ctl1-Auxiliary 2 }

ctl1Aux-BallastPowersTitles OBJECT-TYPE
	SYNTAX      OCTET STRING
	MAX-ACCESS  read-only
	STATUS      current
	DESCRIPTION
		"Ballast Powers Titles (Separator - CrLf)"
        ::= { ctl1-Auxiliary 3 }

ctl1Unit-Connected  OBJECT-TYPE
	SYNTAX      INTEGER {false(0), true(1)}
	MAX-ACCESS  read-only
	STATUS      current
	DESCRIPTION
		""
        ::= { ctl1-Unit 1 }

ctl1Unit-Warning    OBJECT-TYPE
	SYNTAX      INTEGER {false(0), true(1)}
	MAX-ACCESS  read-only
	STATUS      current
	DESCRIPTION
		""
        ::= { ctl1-Unit 2 }

ctl1Unit-Failure    OBJECT-TYPE
	SYNTAX      INTEGER {false(0), true(1)}
	MAX-ACCESS  read-only
	STATUS      current
	DESCRIPTION
		""
        ::= { ctl1-Unit 3 }

ctl1Unit-Busy       OBJECT-TYPE
	SYNTAX      Integer32
	MAX-ACCESS  read-only
	STATUS      current
	DESCRIPTION
		""
        ::= { ctl1-Unit 4 }

ctl1Unit-Model      OBJECT-TYPE
	SYNTAX      OCTET STRING
	MAX-ACCESS  read-only
	STATUS      current
	DESCRIPTION
		""
        ::= { ctl1-Unit 5 }

ctl1Unit-Serial-Number OBJECT-TYPE
	SYNTAX      Integer32
	MAX-ACCESS  read-only
	STATUS      current
	DESCRIPTION
		""
        ::= { ctl1-Unit 6 }

ctl1Unit-Firmware-Version OBJECT-TYPE
	SYNTAX      OCTET STRING
	MAX-ACCESS  read-only
	STATUS      current
	DESCRIPTION
		""
        ::= { ctl1-Unit 7 }

ctl1Unit-Uptime     OBJECT-TYPE
	SYNTAX      DateAndTime
	MAX-ACCESS  read-only
	STATUS      current
	DESCRIPTION
		""
        ::= { ctl1-Unit 8 }

ctl1Unit-Post-Writes-Count OBJECT-TYPE
	SYNTAX      Integer32
	MAX-ACCESS  read-only
	STATUS      current
	DESCRIPTION
		""
        ::= { ctl1-Unit 9 }

ctl1Unit-IP-Address OBJECT-TYPE
	SYNTAX      IPAddress
	MAX-ACCESS  read-only
	STATUS      current
	DESCRIPTION
		""
        ::= { ctl1-Unit 10 }

ctl1Unit-TCP-Port   OBJECT-TYPE
	SYNTAX      Integer32
	MAX-ACCESS  read-only
	STATUS      current
	DESCRIPTION
		""
        ::= { ctl1-Unit 11 }

ctl1Unit-Adapter    OBJECT-TYPE
	SYNTAX      OCTET STRING
	MAX-ACCESS  read-only
	STATUS      current
	DESCRIPTION
		""
        ::= { ctl1-Unit 12 }

ctl1Unit-Reconnects OBJECT-TYPE
	SYNTAX      Integer32
	MAX-ACCESS  read-only
	STATUS      current
	DESCRIPTION
		""
        ::= { ctl1-Unit 13 }

Polaris-SysCtl-sysCtl-Feedback-Command OBJECT-TYPE
	SYNTAX      OCTET STRING
	MAX-ACCESS  read-write
	STATUS      current
	DESCRIPTION
		""
        ::= { Polaris-SysCtl-sysCtl 3 }

Polaris-SysCtl-Ignore-Control-Units OBJECT-TYPE
	SYNTAX      Integer32
	MAX-ACCESS  read-write
	STATUS      current
	DESCRIPTION
		""
        ::= { Polaris-SysCtl-Ignore-Devices 2 }

Polaris-SysCtl-Ignore-Exciters OBJECT-TYPE
	SYNTAX      Integer32
	MAX-ACCESS  read-write
	STATUS      current
	DESCRIPTION
		""
        ::= { Polaris-SysCtl-Ignore-Devices 3 }

Polaris-SysCtl-Ignore-Amplifiers OBJECT-TYPE
	SYNTAX      Integer32
	MAX-ACCESS  read-write
	STATUS      current
	DESCRIPTION
		""
        ::= { Polaris-SysCtl-Ignore-Devices 4 }

Polaris-SysCtl-Ignore-Ballasts OBJECT-TYPE
	SYNTAX      Integer32
	MAX-ACCESS  read-write
	STATUS      current
	DESCRIPTION
		""
        ::= { Polaris-SysCtl-Ignore-Devices 5 }

Polaris-SysCtl-Misc-Reboot-Server OBJECT-TYPE
	SYNTAX      Integer32
	MAX-ACCESS  read-write
	STATUS      current
	DESCRIPTION
		"<unused>"
        ::= { Polaris-SysCtl-Misc 1 }

Polaris-SysCtl-Misc-Date-Time OBJECT-TYPE
	SYNTAX      OCTET STRING
	MAX-ACCESS  read-write
	STATUS      current
	DESCRIPTION
		""
        ::= { Polaris-SysCtl-Misc 2 }

Polaris-SysCtl-Misc-Language OBJECT-TYPE
	SYNTAX      Integer32
	MAX-ACCESS  read-write
	STATUS      current
	DESCRIPTION
		"<unused>"
        ::= { Polaris-SysCtl-Misc 3 }

Polaris-SysCtl-Misc-Restart-Agent OBJECT-TYPE
	SYNTAX      Integer32
	MAX-ACCESS  read-write
	STATUS      current
	DESCRIPTION
		""
        ::= { Polaris-SysCtl-Misc 4 }

Polaris-SysCtl-Misc-Drop-Devices OBJECT-TYPE
	SYNTAX      Integer32
	MAX-ACCESS  read-write
	STATUS      current
	DESCRIPTION
		"<unused>"
        ::= { Polaris-SysCtl-Misc 5 }

Polaris-SysCtl-Misc-Reset-Config OBJECT-TYPE
	SYNTAX      Integer32
	MAX-ACCESS  read-write
	STATUS      current
	DESCRIPTION
		"<unused>"
        ::= { Polaris-SysCtl-Misc 6 }

Polaris-SysCtl-RCS-Model-Code OBJECT-TYPE
	SYNTAX      OCTET STRING
	MAX-ACCESS  read-write
	STATUS      current
	DESCRIPTION
		""
        ::= { Polaris-SysCtl-RCS 2 }

Polaris-SysCtl-RCS-Model-Options OBJECT-TYPE
	SYNTAX      Integer32
	MAX-ACCESS  read-write
	STATUS      current
	DESCRIPTION
		""
        ::= { Polaris-SysCtl-RCS 3 }

Polaris-SysCtl-RCS-Model-Channel OBJECT-TYPE
	SYNTAX      Integer32
	MAX-ACCESS  read-only
	STATUS      current
	DESCRIPTION
		""
        ::= { Polaris-SysCtl-RCS 4 }

Polaris-SysCtl-RCS-Model-Serial-Number OBJECT-TYPE
	SYNTAX      Integer32
	MAX-ACCESS  read-write
	STATUS      current
	DESCRIPTION
		""
        ::= { Polaris-SysCtl-RCS 5 }

Polaris-SysCtl-RCS-Model-Name OBJECT-TYPE
	SYNTAX      OCTET STRING
	MAX-ACCESS  read-write
	STATUS      current
	DESCRIPTION
		""
        ::= { Polaris-SysCtl-RCS 6 }

Polaris-SysCtl-RCS-Base-IP OBJECT-TYPE
	SYNTAX      IPAddress
	MAX-ACCESS  read-write
	STATUS      current
	DESCRIPTION
		""
        ::= { Polaris-SysCtl-RCS 7 }

Polaris-SysCtl-RCS-Base-Port OBJECT-TYPE
	SYNTAX      Integer32
	MAX-ACCESS  read-write
	STATUS      current
	DESCRIPTION
		""
        ::= { Polaris-SysCtl-RCS 8 }

Polaris-SysCtl-RCS-Ports-Mapping OBJECT-TYPE
	SYNTAX      Integer32
	MAX-ACCESS  read-write
	STATUS      current
	DESCRIPTION
		"<unused>"
        ::= { Polaris-SysCtl-RCS 9 }

Polaris-SysCtl-RCS-SCPI-Port OBJECT-TYPE
	SYNTAX      Integer32
	MAX-ACCESS  read-write
	STATUS      current
	DESCRIPTION
		"<unused>"
        ::= { Polaris-SysCtl-RCS 10 }

Polaris-SysCtl-RCS-Use-TCP-Tunnels OBJECT-TYPE
	SYNTAX      Integer32
	MAX-ACCESS  read-write
	STATUS      current
	DESCRIPTION
		"<unused>"
        ::= { Polaris-SysCtl-RCS 11 }

Polaris-SysCtl-RCS-Aux-ID1 OBJECT-TYPE
	SYNTAX      Integer32
	MAX-ACCESS  read-write
	STATUS      current
	DESCRIPTION
		"<unused>"
        ::= { Polaris-SysCtl-RCS 12 }

Polaris-SysCtl-RCS-Aux-ID2 OBJECT-TYPE
	SYNTAX      Integer32
	MAX-ACCESS  read-write
	STATUS      current
	DESCRIPTION
		"<unused>"
        ::= { Polaris-SysCtl-RCS 13 }

Polaris-SysCtl-RCS-Exciters-Base-IP OBJECT-TYPE
	SYNTAX      IPAddress
	MAX-ACCESS  read-write
	STATUS      current
	DESCRIPTION
		"<unused>"
        ::= { Polaris-SysCtl-RCS 14 }

Polaris-SysCtl-RCS-Robust-Connection OBJECT-TYPE
	SYNTAX      Integer32
	MAX-ACCESS  read-write
	STATUS      current
	DESCRIPTION
		"<unused>"
        ::= { Polaris-SysCtl-RCS 15 }

Polaris-SysCtl-SNMPMisc-Send-Comment OBJECT-TYPE
	SYNTAX      OCTET STRING
	MAX-ACCESS  read-write
	STATUS      current
	DESCRIPTION
		""
        ::= { Polaris-SysCtl-SNMP-Misc 1 }

Polaris-SysCtl-SNMPMisc-Web-Username OBJECT-TYPE
	SYNTAX      OCTET STRING
	MAX-ACCESS  read-write
	STATUS      current
	DESCRIPTION
		"length: 0..64 symbols"
        ::= { Polaris-SysCtl-SNMP-Misc 2 }

Polaris-SysCtl-SNMP-Other-Alive-Notifies-Type OBJECT-TYPE
	SYNTAX      INTEGER {disabled (0), trap (1), inform (2)}
	MAX-ACCESS  read-write
	STATUS      current
	DESCRIPTION
		""
        ::= { Polaris-SysCtl-SNMP-Other-Settings 1 }

Polaris-SysCtl-SNMP-Other-Value-Notifies-Type OBJECT-TYPE
	SYNTAX      INTEGER {disabled (0), traps (1), informs (2)}
	MAX-ACCESS  read-write
	STATUS      current
	DESCRIPTION
		""
        ::= { Polaris-SysCtl-SNMP-Other-Settings 2 }

Polaris-SysCtl-SNMP-Other-Alive-Notifies-Period OBJECT-TYPE
	SYNTAX      Integer32
	MAX-ACCESS  read-write
	STATUS      current
	DESCRIPTION
		"seconds, range: 30..3600"
        ::= { Polaris-SysCtl-SNMP-Other-Settings 3 }

Polaris-SysCtl-SNMP-Other-Value-Notifies-Period OBJECT-TYPE
	SYNTAX      Integer32
	MAX-ACCESS  read-write
	STATUS      current
	DESCRIPTION
		"minutes, range: 1..1440"
        ::= { Polaris-SysCtl-SNMP-Other-Settings 4 }

Polaris-SysCtl-SNMP-Other-Informs-ACK-Timeout OBJECT-TYPE
	SYNTAX      Integer32
	MAX-ACCESS  read-write
	STATUS      current
	DESCRIPTION
		"seconds, range: 10..60"
        ::= { Polaris-SysCtl-SNMP-Other-Settings 5 }

Polaris-SysCtl-SNMP-Other-Message-Informs-Queue-Size OBJECT-TYPE
	SYNTAX      Integer32
	MAX-ACCESS  read-write
	STATUS      current
	DESCRIPTION
		"<no units>, range: 5..10000"
        ::= { Polaris-SysCtl-SNMP-Other-Settings 6 }

Polaris-SysCtl-SNMP-Other-Value-Informs-Queue-Size OBJECT-TYPE
	SYNTAX      Integer32
	MAX-ACCESS  read-write
	STATUS      current
	DESCRIPTION
		"<no units>, range: 5..10000"
        ::= { Polaris-SysCtl-SNMP-Other-Settings 7 }

Polaris-SysCtl-SNMP-Other-Status-Notifies-Type OBJECT-TYPE
	SYNTAX      INTEGER {false(0), true(1)}
	MAX-ACCESS  read-write
	STATUS      current
	DESCRIPTION
		""
        ::= { Polaris-SysCtl-SNMP-Other-Settings 8 }

Polaris-SysCtl-SNMP-Other-Status-Notifies-Period OBJECT-TYPE
	SYNTAX      Integer32
	MAX-ACCESS  read-write
	STATUS      current
	DESCRIPTION
		"minutes, range: 0..720, 0: disable periodical sending"
        ::= { Polaris-SysCtl-SNMP-Other-Settings 9 }

Polaris-SysCtl-SNMP-Other-Community-Get OBJECT-TYPE
	SYNTAX      OCTET STRING
	MAX-ACCESS  read-write
	STATUS      current
	DESCRIPTION
		"length: 1..32 symbols"
        ::= { Polaris-SysCtl-SNMP-Other-Settings 10 }

Polaris-SysCtl-SNMP-Other-Community-Set OBJECT-TYPE
	SYNTAX      OCTET STRING
	MAX-ACCESS  read-write
	STATUS      current
	DESCRIPTION
		"length: 1..32 symbols"
        ::= { Polaris-SysCtl-SNMP-Other-Settings 11 }

Polaris-SysCtl-SNMP-Other-Trusted-Network-1 OBJECT-TYPE
	SYNTAX      INTEGER {disabled (0), net_x_x_x_x (1), net_10_x_x_x (2), net_172_x_x_x (3), net_169_254_x_x (4), net_192_168_x_x (5), net_192_168_0_x (6), net_192_168_1_x (7), net_192_168_2_x (8), net_192_168_3_x (9), net_192_168_4_x (10), net_192_168_5_x (11), net_192_168_6_x (12), net_192_168_7_x (13)}
	MAX-ACCESS  read-write
	STATUS      current
	DESCRIPTION
		""
        ::= { Polaris-SysCtl-SNMP-Other-Settings 12 }

Polaris-SysCtl-SNMP-Other-Trusted-Network-2 OBJECT-TYPE
	SYNTAX      OCTET STRING
	MAX-ACCESS  read-write
	STATUS      current
	DESCRIPTION
		"string in CIDR-notation, 0.0.0.0/32 = disabled"
        ::= { Polaris-SysCtl-SNMP-Other-Settings 13 }

Polaris-SysCtl-SNMP-Other-Trusted-Network-3 OBJECT-TYPE
	SYNTAX      OCTET STRING
	MAX-ACCESS  read-write
	STATUS      current
	DESCRIPTION
		"string in CIDR-notation, 0.0.0.0/32 = disabled"
        ::= { Polaris-SysCtl-SNMP-Other-Settings 14 }

Polaris-SysCtl-SNMP-Other-Allow-Get OBJECT-TYPE
	SYNTAX      Integer32
	MAX-ACCESS  read-write
	STATUS      current
	DESCRIPTION
		"bits: 
0: Manager 1 
1: Manager 2 
2: Manager 3 
3: Manager 4 
4: Trusted Network 1 
5: Trusted Network 2 
6: Trusted Network 3 
7+: <UNUSED>, always=0"
        ::= { Polaris-SysCtl-SNMP-Other-Settings 15 }

Polaris-SysCtl-SNMP-Other-Allow-Set OBJECT-TYPE
	SYNTAX      Integer32
	MAX-ACCESS  read-write
	STATUS      current
	DESCRIPTION
		"bits: 
0: Manager 1 
1: Manager 2 
2: Manager 3 
3: Manager 4 
4: Trusted Network 1 
5: Trusted Network 2 
6: Trusted Network 3 
7+: <UNUSED>, always=0"
        ::= { Polaris-SysCtl-SNMP-Other-Settings 16 }

Polaris-SysCtl-SNMP-Other-Local-Logging OBJECT-TYPE
	SYNTAX      INTEGER {false(0), true(1)}
	MAX-ACCESS  read-write
	STATUS      current
	DESCRIPTION
		""
        ::= { Polaris-SysCtl-SNMP-Other-Settings 17 }

Polaris-SysCtl-SNMP-Managers-ID-1 OBJECT-TYPE
	SYNTAX      Integer32
	MAX-ACCESS  read-write
	STATUS      current
	DESCRIPTION
		"<no units>, range: 0..99999"
        ::= { Polaris-SysCtl-SNMP-Managers-ID 1 }

Polaris-SysCtl-SNMP-Managers-ID-2 OBJECT-TYPE
	SYNTAX      Integer32
	MAX-ACCESS  read-write
	STATUS      current
	DESCRIPTION
		"<no units>, range: 0..99999"
        ::= { Polaris-SysCtl-SNMP-Managers-ID 2 }

Polaris-SysCtl-SNMP-Managers-ID-3 OBJECT-TYPE
	SYNTAX      Integer32
	MAX-ACCESS  read-write
	STATUS      current
	DESCRIPTION
		"<no units>, range: 0..99999"
        ::= { Polaris-SysCtl-SNMP-Managers-ID 3 }

Polaris-SysCtl-SNMP-Managers-ID-4 OBJECT-TYPE
	SYNTAX      Integer32
	MAX-ACCESS  read-write
	STATUS      current
	DESCRIPTION
		"<no units>, range: 0..99999"
        ::= { Polaris-SysCtl-SNMP-Managers-ID 4 }

Polaris-SysCtl-SNMP-Managers-Community-1 OBJECT-TYPE
	SYNTAX      OCTET STRING
	MAX-ACCESS  read-write
	STATUS      current
	DESCRIPTION
		"length: 1..32 symbols"
        ::= { Polaris-SysCtl-SNMP-Managers-Community 1 }

Polaris-SysCtl-SNMP-Managers-Community-2 OBJECT-TYPE
	SYNTAX      OCTET STRING
	MAX-ACCESS  read-write
	STATUS      current
	DESCRIPTION
		"length: 1..32 symbols"
        ::= { Polaris-SysCtl-SNMP-Managers-Community 2 }

Polaris-SysCtl-SNMP-Managers-Community-3 OBJECT-TYPE
	SYNTAX      OCTET STRING
	MAX-ACCESS  read-write
	STATUS      current
	DESCRIPTION
		"length: 1..32 symbols"
        ::= { Polaris-SysCtl-SNMP-Managers-Community 3 }

Polaris-SysCtl-SNMP-Managers-Community-4 OBJECT-TYPE
	SYNTAX      OCTET STRING
	MAX-ACCESS  read-write
	STATUS      current
	DESCRIPTION
		"length: 1..32 symbols"
        ::= { Polaris-SysCtl-SNMP-Managers-Community 4 }

Polaris-SysCtl-SNMP-Managers-Port-1 OBJECT-TYPE
	SYNTAX      Integer32
	MAX-ACCESS  read-write
	STATUS      current
	DESCRIPTION
		"<no units>, range: 1..65535"
        ::= { Polaris-SysCtl-SNMP-Managers-Port 1 }

Polaris-SysCtl-SNMP-Managers-Port-2 OBJECT-TYPE
	SYNTAX      Integer32
	MAX-ACCESS  read-write
	STATUS      current
	DESCRIPTION
		"<no units>, range: 1..65535"
        ::= { Polaris-SysCtl-SNMP-Managers-Port 2 }

Polaris-SysCtl-SNMP-Managers-Port-3 OBJECT-TYPE
	SYNTAX      Integer32
	MAX-ACCESS  read-write
	STATUS      current
	DESCRIPTION
		"<no units>, range: 1..65535"
        ::= { Polaris-SysCtl-SNMP-Managers-Port 3 }

Polaris-SysCtl-SNMP-Managers-Port-4 OBJECT-TYPE
	SYNTAX      Integer32
	MAX-ACCESS  read-write
	STATUS      current
	DESCRIPTION
		"<no units>, range: 1..65535"
        ::= { Polaris-SysCtl-SNMP-Managers-Port 4 }

Polaris-SysCtl-SNMP-Managers-IP-1 OBJECT-TYPE
	SYNTAX      IPAddress
	MAX-ACCESS  read-write
	STATUS      current
	DESCRIPTION
		""
        ::= { Polaris-SysCtl-SNMP-Managers-IP 1 }

Polaris-SysCtl-SNMP-Managers-IP-2 OBJECT-TYPE
	SYNTAX      IPAddress
	MAX-ACCESS  read-write
	STATUS      current
	DESCRIPTION
		""
        ::= { Polaris-SysCtl-SNMP-Managers-IP 2 }

Polaris-SysCtl-SNMP-Managers-IP-3 OBJECT-TYPE
	SYNTAX      IPAddress
	MAX-ACCESS  read-write
	STATUS      current
	DESCRIPTION
		""
        ::= { Polaris-SysCtl-SNMP-Managers-IP 3 }

Polaris-SysCtl-SNMP-Managers-IP-4 OBJECT-TYPE
	SYNTAX      IPAddress
	MAX-ACCESS  read-write
	STATUS      current
	DESCRIPTION
		""
        ::= { Polaris-SysCtl-SNMP-Managers-IP 4 }

Polaris-SysDispTrans-Warning OBJECT-TYPE
	SYNTAX      INTEGER {false(0), true(1)}
	MAX-ACCESS  read-only
	STATUS      current
	DESCRIPTION
		""
        ::= { Polaris-SysDisp-Transmitter 1 }

Polaris-SysDispTrans-Failure OBJECT-TYPE
	SYNTAX      INTEGER {false(0), true(1)}
	MAX-ACCESS  read-only
	STATUS      current
	DESCRIPTION
		""
        ::= { Polaris-SysDisp-Transmitter 2 }

Polaris-SysDispTransRemoteLogState OBJECT-TYPE
	SYNTAX      INTEGER {notConnected (0), normal (1), warnings (2), failures (3)}
	MAX-ACCESS  read-only
	STATUS      current
	DESCRIPTION
		""
        ::= { Polaris-SysDisp-Transmitter 10 }

Polaris-SysDisp-SNMP-Stat-SNMP-Other-Last-Inform-ACK-Time OBJECT-TYPE
	SYNTAX      Integer32
	MAX-ACCESS  read-only
	STATUS      current
	DESCRIPTION
		"ms"
        ::= { Polaris-SysDisp-SNMP-Stat-SNMP-Other 1 }

Polaris-SysDisp-SNMP-Stat-SNMP-Other-Inform-ACK-Max-Time OBJECT-TYPE
	SYNTAX      Integer32
	MAX-ACCESS  read-only
	STATUS      current
	DESCRIPTION
		"ms"
        ::= { Polaris-SysDisp-SNMP-Stat-SNMP-Other 2 }

Polaris-SysDisp-SNMP-Stat-SNMP-Thread-Outcoming-Packets-Count OBJECT-TYPE
	SYNTAX      Integer32
	MAX-ACCESS  read-only
	STATUS      current
	DESCRIPTION
		""
        ::= { Polaris-SysDisp-SNMP-Stat-SNMP-Thread-Monitoring 1 }

Polaris-SysDisp-SNMP-Stat-SNMP-Thread-Unconfirmed-Messages-Count OBJECT-TYPE
	SYNTAX      Integer32
	MAX-ACCESS  read-only
	STATUS      current
	DESCRIPTION
		""
        ::= { Polaris-SysDisp-SNMP-Stat-SNMP-Thread-Monitoring 2 }

Polaris-SysDisp-SNMP-Stat-SNMP-Thread-Undelivered-Messages-Count OBJECT-TYPE
	SYNTAX      Integer32
	MAX-ACCESS  read-only
	STATUS      current
	DESCRIPTION
		""
        ::= { Polaris-SysDisp-SNMP-Stat-SNMP-Thread-Monitoring 3 }

Polaris-SysDisp-SNMP-Stat-Access-Err-Counter-Last-Access-Error-Text OBJECT-TYPE
	SYNTAX      OCTET STRING
	MAX-ACCESS  read-only
	STATUS      current
	DESCRIPTION
		""
        ::= { Polaris-SysDisp-SNMP-Stat-Access-Errors-Counters 1 }

Polaris-SysDisp-SNMP-Stat-Access-Err-Counter-Trap-V1 OBJECT-TYPE
	SYNTAX      Integer32
	MAX-ACCESS  read-only
	STATUS      current
	DESCRIPTION
		""
        ::= { Polaris-SysDisp-SNMP-Stat-Access-Errors-Counters 2 }

Polaris-SysDisp-SNMP-Stat-Access-Err-Counter-Trap-V2 OBJECT-TYPE
	SYNTAX      Integer32
	MAX-ACCESS  read-only
	STATUS      current
	DESCRIPTION
		""
        ::= { Polaris-SysDisp-SNMP-Stat-Access-Errors-Counters 3 }

Polaris-SysDisp-SNMP-Stat-Access-Err-Counter-Inform OBJECT-TYPE
	SYNTAX      Integer32
	MAX-ACCESS  read-only
	STATUS      current
	DESCRIPTION
		""
        ::= { Polaris-SysDisp-SNMP-Stat-Access-Errors-Counters 4 }

Polaris-SysDisp-SNMP-Stat-Access-Err-Counter-Get OBJECT-TYPE
	SYNTAX      Integer32
	MAX-ACCESS  read-only
	STATUS      current
	DESCRIPTION
		""
        ::= { Polaris-SysDisp-SNMP-Stat-Access-Errors-Counters 5 }

Polaris-SysDisp-SNMP-Stat-Access-Err-Counter-Get-Next OBJECT-TYPE
	SYNTAX      Integer32
	MAX-ACCESS  read-only
	STATUS      current
	DESCRIPTION
		""
        ::= { Polaris-SysDisp-SNMP-Stat-Access-Errors-Counters 6 }

Polaris-SysDisp-SNMP-Stat-Access-Err-Counter-Get-Bulk OBJECT-TYPE
	SYNTAX      Integer32
	MAX-ACCESS  read-only
	STATUS      current
	DESCRIPTION
		""
        ::= { Polaris-SysDisp-SNMP-Stat-Access-Errors-Counters 7 }

Polaris-SysDisp-SNMP-Stat-Access-Err-Counter-Set OBJECT-TYPE
	SYNTAX      Integer32
	MAX-ACCESS  read-only
	STATUS      current
	DESCRIPTION
		""
        ::= { Polaris-SysDisp-SNMP-Stat-Access-Errors-Counters 8 }

Polaris-SysDisp-SNMP-Stat-SNMP-Inf-Mng-4-Alive-Total-Created OBJECT-TYPE
	SYNTAX      Integer32
	MAX-ACCESS  read-only
	STATUS      current
	DESCRIPTION
		"<no units>"
        ::= { Polaris-SysDisp-SNMP-Stat-SNMP-Inf-Manager-4 1 }

Polaris-SysDisp-SNMP-Stat-SNMP-Inf-Mng-4-Alive-REQ OBJECT-TYPE
	SYNTAX      Integer32
	MAX-ACCESS  read-only
	STATUS      current
	DESCRIPTION
		"<no units>"
        ::= { Polaris-SysDisp-SNMP-Stat-SNMP-Inf-Manager-4 2 }

Polaris-SysDisp-SNMP-Stat-SNMP-Inf-Mng-4-Alive-ACK OBJECT-TYPE
	SYNTAX      Integer32
	MAX-ACCESS  read-only
	STATUS      current
	DESCRIPTION
		"<no units>"
        ::= { Polaris-SysDisp-SNMP-Stat-SNMP-Inf-Manager-4 3 }

Polaris-SysDisp-SNMP-Stat-SNMP-Inf-Mng-4-Alive-NoACK-global OBJECT-TYPE
	SYNTAX      Integer32
	MAX-ACCESS  read-only
	STATUS      current
	DESCRIPTION
		"<no units>"
        ::= { Polaris-SysDisp-SNMP-Stat-SNMP-Inf-Manager-4 4 }

Polaris-SysDisp-SNMP-Stat-SNMP-Inf-Mng-4-Alive-NoACK-local OBJECT-TYPE
	SYNTAX      Integer32
	MAX-ACCESS  read-only
	STATUS      current
	DESCRIPTION
		"<no units>"
        ::= { Polaris-SysDisp-SNMP-Stat-SNMP-Inf-Manager-4 5 }

Polaris-SysDisp-SNMP-Stat-SNMP-Inf-Mng-4-Value-Total-Created OBJECT-TYPE
	SYNTAX      Integer32
	MAX-ACCESS  read-only
	STATUS      current
	DESCRIPTION
		"<no units>"
        ::= { Polaris-SysDisp-SNMP-Stat-SNMP-Inf-Manager-4 6 }

Polaris-SysDisp-SNMP-Stat-SNMP-Inf-Mng-4-Value-REQ OBJECT-TYPE
	SYNTAX      Integer32
	MAX-ACCESS  read-only
	STATUS      current
	DESCRIPTION
		"<no units>"
        ::= { Polaris-SysDisp-SNMP-Stat-SNMP-Inf-Manager-4 7 }

Polaris-SysDisp-SNMP-Stat-SNMP-Inf-Mng-4-Value-ACK OBJECT-TYPE
	SYNTAX      Integer32
	MAX-ACCESS  read-only
	STATUS      current
	DESCRIPTION
		"<no units>"
        ::= { Polaris-SysDisp-SNMP-Stat-SNMP-Inf-Manager-4 8 }

Polaris-SysDisp-SNMP-Stat-SNMP-Inf-Mng-4-Value-NoACK-global OBJECT-TYPE
	SYNTAX      Integer32
	MAX-ACCESS  read-only
	STATUS      current
	DESCRIPTION
		"<no units>"
        ::= { Polaris-SysDisp-SNMP-Stat-SNMP-Inf-Manager-4 9 }

Polaris-SysDisp-SNMP-Stat-SNMP-Inf-Mng-4-Value-NoACK-local OBJECT-TYPE
	SYNTAX      Integer32
	MAX-ACCESS  read-only
	STATUS      current
	DESCRIPTION
		"<no units>"
        ::= { Polaris-SysDisp-SNMP-Stat-SNMP-Inf-Manager-4 10 }

Polaris-SysDisp-SNMP-Stat-SNMP-Inf-Mng-4-Value-FIFO-Load-Percent OBJECT-TYPE
	SYNTAX      Integer32
	MAX-ACCESS  read-only
	STATUS      current
	DESCRIPTION
		"% * 10"
        ::= { Polaris-SysDisp-SNMP-Stat-SNMP-Inf-Manager-4 11 }

Polaris-SysDisp-SNMP-Stat-SNMP-Inf-Mng-4-Value-FIFO-Load-Number OBJECT-TYPE
	SYNTAX      Integer32
	MAX-ACCESS  read-only
	STATUS      current
	DESCRIPTION
		"<no units>"
        ::= { Polaris-SysDisp-SNMP-Stat-SNMP-Inf-Manager-4 12 }

Polaris-SysDisp-SNMP-Stat-SNMP-Inf-Mng-4-Value-FIFO-Lost OBJECT-TYPE
	SYNTAX      Integer32
	MAX-ACCESS  read-only
	STATUS      current
	DESCRIPTION
		"<no units>"
        ::= { Polaris-SysDisp-SNMP-Stat-SNMP-Inf-Manager-4 13 }

Polaris-SysDisp-SNMP-Stat-SNMP-Inf-Mng-4-Message-Total-Created OBJECT-TYPE
	SYNTAX      Integer32
	MAX-ACCESS  read-only
	STATUS      current
	DESCRIPTION
		"<no units>"
        ::= { Polaris-SysDisp-SNMP-Stat-SNMP-Inf-Manager-4 14 }

Polaris-SysDisp-SNMP-Stat-SNMP-Inf-Mng-4-Message-REQ OBJECT-TYPE
	SYNTAX      Integer32
	MAX-ACCESS  read-only
	STATUS      current
	DESCRIPTION
		"<no units>"
        ::= { Polaris-SysDisp-SNMP-Stat-SNMP-Inf-Manager-4 15 }

Polaris-SysDisp-SNMP-Stat-SNMP-Inf-Mng-4-Message-ACK OBJECT-TYPE
	SYNTAX      Integer32
	MAX-ACCESS  read-only
	STATUS      current
	DESCRIPTION
		"<no units>"
        ::= { Polaris-SysDisp-SNMP-Stat-SNMP-Inf-Manager-4 16 }

Polaris-SysDisp-SNMP-Stat-SNMP-Inf-Mng-4-Message-NoACK-global OBJECT-TYPE
	SYNTAX      Integer32
	MAX-ACCESS  read-only
	STATUS      current
	DESCRIPTION
		"<no units>"
        ::= { Polaris-SysDisp-SNMP-Stat-SNMP-Inf-Manager-4 17 }

Polaris-SysDisp-SNMP-Stat-SNMP-Inf-Mng-4-Message-NoACK-local OBJECT-TYPE
	SYNTAX      Integer32
	MAX-ACCESS  read-only
	STATUS      current
	DESCRIPTION
		"<no units>"
        ::= { Polaris-SysDisp-SNMP-Stat-SNMP-Inf-Manager-4 18 }

Polaris-SysDisp-SNMP-Stat-SNMP-Inf-Mng-4-Message-FIFO-Load-Percent OBJECT-TYPE
	SYNTAX      Integer32
	MAX-ACCESS  read-only
	STATUS      current
	DESCRIPTION
		"% * 10"
        ::= { Polaris-SysDisp-SNMP-Stat-SNMP-Inf-Manager-4 19 }

Polaris-SysDisp-SNMP-Stat-SNMP-Inf-Mng-4-Message-FIFO-Load-Number OBJECT-TYPE
	SYNTAX      Integer32
	MAX-ACCESS  read-only
	STATUS      current
	DESCRIPTION
		"<no units>"
        ::= { Polaris-SysDisp-SNMP-Stat-SNMP-Inf-Manager-4 20 }

Polaris-SysDisp-SNMP-Stat-SNMP-Inf-Mng-4-Message-FIFO-Lost OBJECT-TYPE
	SYNTAX      Integer32
	MAX-ACCESS  read-only
	STATUS      current
	DESCRIPTION
		"<no units>"
        ::= { Polaris-SysDisp-SNMP-Stat-SNMP-Inf-Manager-4 21 }

Polaris-SysDisp-SNMP-Stat-SNMP-Inf-Mng-4-Status-Total-Created OBJECT-TYPE
	SYNTAX      Integer32
	MAX-ACCESS  read-only
	STATUS      current
	DESCRIPTION
		"<no units>"
        ::= { Polaris-SysDisp-SNMP-Stat-SNMP-Inf-Manager-4 22 }

Polaris-SysDisp-SNMP-Stat-SNMP-Inf-Mng-4-Status-REQ OBJECT-TYPE
	SYNTAX      Integer32
	MAX-ACCESS  read-only
	STATUS      current
	DESCRIPTION
		"<no units>"
        ::= { Polaris-SysDisp-SNMP-Stat-SNMP-Inf-Manager-4 23 }

Polaris-SysDisp-SNMP-Stat-SNMP-Inf-Mng-4-Status-ACK OBJECT-TYPE
	SYNTAX      Integer32
	MAX-ACCESS  read-only
	STATUS      current
	DESCRIPTION
		"<no units>"
        ::= { Polaris-SysDisp-SNMP-Stat-SNMP-Inf-Manager-4 24 }

Polaris-SysDisp-SNMP-Stat-SNMP-Inf-Mng-4-Status-NoACK-global OBJECT-TYPE
	SYNTAX      Integer32
	MAX-ACCESS  read-only
	STATUS      current
	DESCRIPTION
		"<no units>"
        ::= { Polaris-SysDisp-SNMP-Stat-SNMP-Inf-Manager-4 25 }

Polaris-SysDisp-SNMP-Stat-SNMP-Inf-Mng-4-Status-NoACK-local OBJECT-TYPE
	SYNTAX      Integer32
	MAX-ACCESS  read-only
	STATUS      current
	DESCRIPTION
		"<no units>"
        ::= { Polaris-SysDisp-SNMP-Stat-SNMP-Inf-Manager-4 26 }

Polaris-SysDisp-SNMP-Stat-SNMP-Inf-Mng-4-Status-Replaced OBJECT-TYPE
	SYNTAX      Integer32
	MAX-ACCESS  read-only
	STATUS      current
	DESCRIPTION
		"<no units>"
        ::= { Polaris-SysDisp-SNMP-Stat-SNMP-Inf-Manager-4 27 }

Polaris-SysDisp-SNMP-Stat-SNMP-Inf-Mng-3-Alive-Total-Created OBJECT-TYPE
	SYNTAX      Integer32
	MAX-ACCESS  read-only
	STATUS      current
	DESCRIPTION
		"<no units>"
        ::= { Polaris-SysDisp-SNMP-Stat-SNMP-Inf-Manager-3 1 }

Polaris-SysDisp-SNMP-Stat-SNMP-Inf-Mng-3-Alive-REQ OBJECT-TYPE
	SYNTAX      Integer32
	MAX-ACCESS  read-only
	STATUS      current
	DESCRIPTION
		"<no units>"
        ::= { Polaris-SysDisp-SNMP-Stat-SNMP-Inf-Manager-3 2 }

Polaris-SysDisp-SNMP-Stat-SNMP-Inf-Mng-3-Alive-ACK OBJECT-TYPE
	SYNTAX      Integer32
	MAX-ACCESS  read-only
	STATUS      current
	DESCRIPTION
		"<no units>"
        ::= { Polaris-SysDisp-SNMP-Stat-SNMP-Inf-Manager-3 3 }

Polaris-SysDisp-SNMP-Stat-SNMP-Inf-Mng-3-Alive-NoACK-global OBJECT-TYPE
	SYNTAX      Integer32
	MAX-ACCESS  read-only
	STATUS      current
	DESCRIPTION
		"<no units>"
        ::= { Polaris-SysDisp-SNMP-Stat-SNMP-Inf-Manager-3 4 }

Polaris-SysDisp-SNMP-Stat-SNMP-Inf-Mng-3-Alive-NoACK-local OBJECT-TYPE
	SYNTAX      Integer32
	MAX-ACCESS  read-only
	STATUS      current
	DESCRIPTION
		"<no units>"
        ::= { Polaris-SysDisp-SNMP-Stat-SNMP-Inf-Manager-3 5 }

Polaris-SysDisp-SNMP-Stat-SNMP-Inf-Mng-3-Value-Total-Created OBJECT-TYPE
	SYNTAX      Integer32
	MAX-ACCESS  read-only
	STATUS      current
	DESCRIPTION
		"<no units>"
        ::= { Polaris-SysDisp-SNMP-Stat-SNMP-Inf-Manager-3 6 }

Polaris-SysDisp-SNMP-Stat-SNMP-Inf-Mng-3-Value-REQ OBJECT-TYPE
	SYNTAX      Integer32
	MAX-ACCESS  read-only
	STATUS      current
	DESCRIPTION
		"<no units>"
        ::= { Polaris-SysDisp-SNMP-Stat-SNMP-Inf-Manager-3 7 }

Polaris-SysDisp-SNMP-Stat-SNMP-Inf-Mng-3-Value-ACK OBJECT-TYPE
	SYNTAX      Integer32
	MAX-ACCESS  read-only
	STATUS      current
	DESCRIPTION
		"<no units>"
        ::= { Polaris-SysDisp-SNMP-Stat-SNMP-Inf-Manager-3 8 }

Polaris-SysDisp-SNMP-Stat-SNMP-Inf-Mng-3-Value-NoACK-global OBJECT-TYPE
	SYNTAX      Integer32
	MAX-ACCESS  read-only
	STATUS      current
	DESCRIPTION
		"<no units>"
        ::= { Polaris-SysDisp-SNMP-Stat-SNMP-Inf-Manager-3 9 }

Polaris-SysDisp-SNMP-Stat-SNMP-Inf-Mng-3-Value-NoACK-local OBJECT-TYPE
	SYNTAX      Integer32
	MAX-ACCESS  read-only
	STATUS      current
	DESCRIPTION
		"<no units>"
        ::= { Polaris-SysDisp-SNMP-Stat-SNMP-Inf-Manager-3 10 }

Polaris-SysDisp-SNMP-Stat-SNMP-Inf-Mng-3-Value-FIFO-Load-Percent OBJECT-TYPE
	SYNTAX      Integer32
	MAX-ACCESS  read-only
	STATUS      current
	DESCRIPTION
		"% * 10"
        ::= { Polaris-SysDisp-SNMP-Stat-SNMP-Inf-Manager-3 11 }

Polaris-SysDisp-SNMP-Stat-SNMP-Inf-Mng-3-Value-FIFO-Load-Number OBJECT-TYPE
	SYNTAX      Integer32
	MAX-ACCESS  read-only
	STATUS      current
	DESCRIPTION
		"<no units>"
        ::= { Polaris-SysDisp-SNMP-Stat-SNMP-Inf-Manager-3 12 }

Polaris-SysDisp-SNMP-Stat-SNMP-Inf-Mng-3-Value-FIFO-Lost OBJECT-TYPE
	SYNTAX      Integer32
	MAX-ACCESS  read-only
	STATUS      current
	DESCRIPTION
		"<no units>"
        ::= { Polaris-SysDisp-SNMP-Stat-SNMP-Inf-Manager-3 13 }

Polaris-SysDisp-SNMP-Stat-SNMP-Inf-Mng-3-Message-Total-Created OBJECT-TYPE
	SYNTAX      Integer32
	MAX-ACCESS  read-only
	STATUS      current
	DESCRIPTION
		"<no units>"
        ::= { Polaris-SysDisp-SNMP-Stat-SNMP-Inf-Manager-3 14 }

Polaris-SysDisp-SNMP-Stat-SNMP-Inf-Mng-3-Message-REQ OBJECT-TYPE
	SYNTAX      Integer32
	MAX-ACCESS  read-only
	STATUS      current
	DESCRIPTION
		"<no units>"
        ::= { Polaris-SysDisp-SNMP-Stat-SNMP-Inf-Manager-3 15 }

Polaris-SysDisp-SNMP-Stat-SNMP-Inf-Mng-3-Message-ACK OBJECT-TYPE
	SYNTAX      Integer32
	MAX-ACCESS  read-only
	STATUS      current
	DESCRIPTION
		"<no units>"
        ::= { Polaris-SysDisp-SNMP-Stat-SNMP-Inf-Manager-3 16 }

Polaris-SysDisp-SNMP-Stat-SNMP-Inf-Mng-3-Message-NoACK-global OBJECT-TYPE
	SYNTAX      Integer32
	MAX-ACCESS  read-only
	STATUS      current
	DESCRIPTION
		"<no units>"
        ::= { Polaris-SysDisp-SNMP-Stat-SNMP-Inf-Manager-3 17 }

Polaris-SysDisp-SNMP-Stat-SNMP-Inf-Mng-3-Message-NoACK-local OBJECT-TYPE
	SYNTAX      Integer32
	MAX-ACCESS  read-only
	STATUS      current
	DESCRIPTION
		"<no units>"
        ::= { Polaris-SysDisp-SNMP-Stat-SNMP-Inf-Manager-3 18 }

Polaris-SysDisp-SNMP-Stat-SNMP-Inf-Mng-3-Message-FIFO-Load-Percent OBJECT-TYPE
	SYNTAX      Integer32
	MAX-ACCESS  read-only
	STATUS      current
	DESCRIPTION
		"% * 10"
        ::= { Polaris-SysDisp-SNMP-Stat-SNMP-Inf-Manager-3 19 }

Polaris-SysDisp-SNMP-Stat-SNMP-Inf-Mng-3-Message-FIFO-Load-Number OBJECT-TYPE
	SYNTAX      Integer32
	MAX-ACCESS  read-only
	STATUS      current
	DESCRIPTION
		"<no units>"
        ::= { Polaris-SysDisp-SNMP-Stat-SNMP-Inf-Manager-3 20 }

Polaris-SysDisp-SNMP-Stat-SNMP-Inf-Mng-3-Message-FIFO-Lost OBJECT-TYPE
	SYNTAX      Integer32
	MAX-ACCESS  read-only
	STATUS      current
	DESCRIPTION
		"<no units>"
        ::= { Polaris-SysDisp-SNMP-Stat-SNMP-Inf-Manager-3 21 }

Polaris-SysDisp-SNMP-Stat-SNMP-Inf-Mng-3-Status-Total-Created OBJECT-TYPE
	SYNTAX      Integer32
	MAX-ACCESS  read-only
	STATUS      current
	DESCRIPTION
		"<no units>"
        ::= { Polaris-SysDisp-SNMP-Stat-SNMP-Inf-Manager-3 22 }

Polaris-SysDisp-SNMP-Stat-SNMP-Inf-Mng-3-Status-REQ OBJECT-TYPE
	SYNTAX      Integer32
	MAX-ACCESS  read-only
	STATUS      current
	DESCRIPTION
		"<no units>"
        ::= { Polaris-SysDisp-SNMP-Stat-SNMP-Inf-Manager-3 23 }

Polaris-SysDisp-SNMP-Stat-SNMP-Inf-Mng-3-Status-ACK OBJECT-TYPE
	SYNTAX      Integer32
	MAX-ACCESS  read-only
	STATUS      current
	DESCRIPTION
		"<no units>"
        ::= { Polaris-SysDisp-SNMP-Stat-SNMP-Inf-Manager-3 24 }

Polaris-SysDisp-SNMP-Stat-SNMP-Inf-Mng-3-Status-NoACK-global OBJECT-TYPE
	SYNTAX      Integer32
	MAX-ACCESS  read-only
	STATUS      current
	DESCRIPTION
		"<no units>"
        ::= { Polaris-SysDisp-SNMP-Stat-SNMP-Inf-Manager-3 25 }

Polaris-SysDisp-SNMP-Stat-SNMP-Inf-Mng-3-Status-NoACK-local OBJECT-TYPE
	SYNTAX      Integer32
	MAX-ACCESS  read-only
	STATUS      current
	DESCRIPTION
		"<no units>"
        ::= { Polaris-SysDisp-SNMP-Stat-SNMP-Inf-Manager-3 26 }

Polaris-SysDisp-SNMP-Stat-SNMP-Inf-Mng-3-Status-Replaced OBJECT-TYPE
	SYNTAX      Integer32
	MAX-ACCESS  read-only
	STATUS      current
	DESCRIPTION
		"<no units>"
        ::= { Polaris-SysDisp-SNMP-Stat-SNMP-Inf-Manager-3 27 }

Polaris-SysDisp-SNMP-Stat-SNMP-Inf-Mng-2-Alive-Total-Created OBJECT-TYPE
	SYNTAX      Integer32
	MAX-ACCESS  read-only
	STATUS      current
	DESCRIPTION
		"<no units>"
        ::= { Polaris-SysDisp-SNMP-Stat-SNMP-Inf-Manager-2 1 }

Polaris-SysDisp-SNMP-Stat-SNMP-Inf-Mng-2-Alive-REQ OBJECT-TYPE
	SYNTAX      Integer32
	MAX-ACCESS  read-only
	STATUS      current
	DESCRIPTION
		"<no units>"
        ::= { Polaris-SysDisp-SNMP-Stat-SNMP-Inf-Manager-2 2 }

Polaris-SysDisp-SNMP-Stat-SNMP-Inf-Mng-2-Alive-ACK OBJECT-TYPE
	SYNTAX      Integer32
	MAX-ACCESS  read-only
	STATUS      current
	DESCRIPTION
		"<no units>"
        ::= { Polaris-SysDisp-SNMP-Stat-SNMP-Inf-Manager-2 3 }

Polaris-SysDisp-SNMP-Stat-SNMP-Inf-Mng-2-Alive-NoACK-global OBJECT-TYPE
	SYNTAX      Integer32
	MAX-ACCESS  read-only
	STATUS      current
	DESCRIPTION
		"<no units>"
        ::= { Polaris-SysDisp-SNMP-Stat-SNMP-Inf-Manager-2 4 }

Polaris-SysDisp-SNMP-Stat-SNMP-Inf-Mng-2-Alive-NoACK-local OBJECT-TYPE
	SYNTAX      Integer32
	MAX-ACCESS  read-only
	STATUS      current
	DESCRIPTION
		"<no units>"
        ::= { Polaris-SysDisp-SNMP-Stat-SNMP-Inf-Manager-2 5 }

Polaris-SysDisp-SNMP-Stat-SNMP-Inf-Mng-2-Value-Total-Created OBJECT-TYPE
	SYNTAX      Integer32
	MAX-ACCESS  read-only
	STATUS      current
	DESCRIPTION
		"<no units>"
        ::= { Polaris-SysDisp-SNMP-Stat-SNMP-Inf-Manager-2 6 }

Polaris-SysDisp-SNMP-Stat-SNMP-Inf-Mng-2-Value-REQ OBJECT-TYPE
	SYNTAX      Integer32
	MAX-ACCESS  read-only
	STATUS      current
	DESCRIPTION
		"<no units>"
        ::= { Polaris-SysDisp-SNMP-Stat-SNMP-Inf-Manager-2 7 }

Polaris-SysDisp-SNMP-Stat-SNMP-Inf-Mng-2-Value-ACK OBJECT-TYPE
	SYNTAX      Integer32
	MAX-ACCESS  read-only
	STATUS      current
	DESCRIPTION
		"<no units>"
        ::= { Polaris-SysDisp-SNMP-Stat-SNMP-Inf-Manager-2 8 }

Polaris-SysDisp-SNMP-Stat-SNMP-Inf-Mng-2-Value-NoACK-global OBJECT-TYPE
	SYNTAX      Integer32
	MAX-ACCESS  read-only
	STATUS      current
	DESCRIPTION
		"<no units>"
        ::= { Polaris-SysDisp-SNMP-Stat-SNMP-Inf-Manager-2 9 }

Polaris-SysDisp-SNMP-Stat-SNMP-Inf-Mng-2-Value-NoACK-local OBJECT-TYPE
	SYNTAX      Integer32
	MAX-ACCESS  read-only
	STATUS      current
	DESCRIPTION
		"<no units>"
        ::= { Polaris-SysDisp-SNMP-Stat-SNMP-Inf-Manager-2 10 }

Polaris-SysDisp-SNMP-Stat-SNMP-Inf-Mng-2-Value-FIFO-Load-Percent OBJECT-TYPE
	SYNTAX      Integer32
	MAX-ACCESS  read-only
	STATUS      current
	DESCRIPTION
		"% * 10"
        ::= { Polaris-SysDisp-SNMP-Stat-SNMP-Inf-Manager-2 11 }

Polaris-SysDisp-SNMP-Stat-SNMP-Inf-Mng-2-Value-FIFO-Load-Number OBJECT-TYPE
	SYNTAX      Integer32
	MAX-ACCESS  read-only
	STATUS      current
	DESCRIPTION
		"<no units>"
        ::= { Polaris-SysDisp-SNMP-Stat-SNMP-Inf-Manager-2 12 }

Polaris-SysDisp-SNMP-Stat-SNMP-Inf-Mng-2-Value-FIFO-Lost OBJECT-TYPE
	SYNTAX      Integer32
	MAX-ACCESS  read-only
	STATUS      current
	DESCRIPTION
		"<no units>"
        ::= { Polaris-SysDisp-SNMP-Stat-SNMP-Inf-Manager-2 13 }

Polaris-SysDisp-SNMP-Stat-SNMP-Inf-Mng-2-Message-Total-Created OBJECT-TYPE
	SYNTAX      Integer32
	MAX-ACCESS  read-only
	STATUS      current
	DESCRIPTION
		"<no units>"
        ::= { Polaris-SysDisp-SNMP-Stat-SNMP-Inf-Manager-2 14 }

Polaris-SysDisp-SNMP-Stat-SNMP-Inf-Mng-2-Message-REQ OBJECT-TYPE
	SYNTAX      Integer32
	MAX-ACCESS  read-only
	STATUS      current
	DESCRIPTION
		"<no units>"
        ::= { Polaris-SysDisp-SNMP-Stat-SNMP-Inf-Manager-2 15 }

Polaris-SysDisp-SNMP-Stat-SNMP-Inf-Mng-2-Message-ACK OBJECT-TYPE
	SYNTAX      Integer32
	MAX-ACCESS  read-only
	STATUS      current
	DESCRIPTION
		"<no units>"
        ::= { Polaris-SysDisp-SNMP-Stat-SNMP-Inf-Manager-2 16 }

Polaris-SysDisp-SNMP-Stat-SNMP-Inf-Mng-2-Message-NoACK-global OBJECT-TYPE
	SYNTAX      Integer32
	MAX-ACCESS  read-only
	STATUS      current
	DESCRIPTION
		"<no units>"
        ::= { Polaris-SysDisp-SNMP-Stat-SNMP-Inf-Manager-2 17 }

Polaris-SysDisp-SNMP-Stat-SNMP-Inf-Mng-2-Message-NoACK-local OBJECT-TYPE
	SYNTAX      Integer32
	MAX-ACCESS  read-only
	STATUS      current
	DESCRIPTION
		"<no units>"
        ::= { Polaris-SysDisp-SNMP-Stat-SNMP-Inf-Manager-2 18 }

Polaris-SysDisp-SNMP-Stat-SNMP-Inf-Mng-2-Message-FIFO-Load-Percent OBJECT-TYPE
	SYNTAX      Integer32
	MAX-ACCESS  read-only
	STATUS      current
	DESCRIPTION
		"% * 10"
        ::= { Polaris-SysDisp-SNMP-Stat-SNMP-Inf-Manager-2 19 }

Polaris-SysDisp-SNMP-Stat-SNMP-Inf-Mng-2-Message-FIFO-Load-Number OBJECT-TYPE
	SYNTAX      Integer32
	MAX-ACCESS  read-only
	STATUS      current
	DESCRIPTION
		"<no units>"
        ::= { Polaris-SysDisp-SNMP-Stat-SNMP-Inf-Manager-2 20 }

Polaris-SysDisp-SNMP-Stat-SNMP-Inf-Mng-2-Message-FIFO-Lost OBJECT-TYPE
	SYNTAX      Integer32
	MAX-ACCESS  read-only
	STATUS      current
	DESCRIPTION
		"<no units>"
        ::= { Polaris-SysDisp-SNMP-Stat-SNMP-Inf-Manager-2 21 }

Polaris-SysDisp-SNMP-Stat-SNMP-Inf-Mng-2-Status-Total-Created OBJECT-TYPE
	SYNTAX      Integer32
	MAX-ACCESS  read-only
	STATUS      current
	DESCRIPTION
		"<no units>"
        ::= { Polaris-SysDisp-SNMP-Stat-SNMP-Inf-Manager-2 22 }

Polaris-SysDisp-SNMP-Stat-SNMP-Inf-Mng-2-Status-REQ OBJECT-TYPE
	SYNTAX      Integer32
	MAX-ACCESS  read-only
	STATUS      current
	DESCRIPTION
		"<no units>"
        ::= { Polaris-SysDisp-SNMP-Stat-SNMP-Inf-Manager-2 23 }

Polaris-SysDisp-SNMP-Stat-SNMP-Inf-Mng-2-Status-ACK OBJECT-TYPE
	SYNTAX      Integer32
	MAX-ACCESS  read-only
	STATUS      current
	DESCRIPTION
		"<no units>"
        ::= { Polaris-SysDisp-SNMP-Stat-SNMP-Inf-Manager-2 24 }

Polaris-SysDisp-SNMP-Stat-SNMP-Inf-Mng-2-Status-NoACK-global OBJECT-TYPE
	SYNTAX      Integer32
	MAX-ACCESS  read-only
	STATUS      current
	DESCRIPTION
		"<no units>"
        ::= { Polaris-SysDisp-SNMP-Stat-SNMP-Inf-Manager-2 25 }

Polaris-SysDisp-SNMP-Stat-SNMP-Inf-Mng-2-Status-NoACK-local OBJECT-TYPE
	SYNTAX      Integer32
	MAX-ACCESS  read-only
	STATUS      current
	DESCRIPTION
		"<no units>"
        ::= { Polaris-SysDisp-SNMP-Stat-SNMP-Inf-Manager-2 26 }

Polaris-SysDisp-SNMP-Stat-SNMP-Inf-Mng-2-Status-Replaced OBJECT-TYPE
	SYNTAX      Integer32
	MAX-ACCESS  read-only
	STATUS      current
	DESCRIPTION
		"<no units>"
        ::= { Polaris-SysDisp-SNMP-Stat-SNMP-Inf-Manager-2 27 }

Polaris-SysDisp-SNMP-Stat-SNMP-Inf-Mng-1-Alive-Total-Created OBJECT-TYPE
	SYNTAX      Integer32
	MAX-ACCESS  read-only
	STATUS      current
	DESCRIPTION
		"<no units>"
        ::= { Polaris-SysDisp-SNMP-Stat-SNMP-Inf-Manager-1 1 }

Polaris-SysDisp-SNMP-Stat-SNMP-Inf-Mng-1-Alive-REQ OBJECT-TYPE
	SYNTAX      Integer32
	MAX-ACCESS  read-only
	STATUS      current
	DESCRIPTION
		"<no units>"
        ::= { Polaris-SysDisp-SNMP-Stat-SNMP-Inf-Manager-1 2 }

Polaris-SysDisp-SNMP-Stat-SNMP-Inf-Mng-1-Alive-ACK OBJECT-TYPE
	SYNTAX      Integer32
	MAX-ACCESS  read-only
	STATUS      current
	DESCRIPTION
		"<no units>"
        ::= { Polaris-SysDisp-SNMP-Stat-SNMP-Inf-Manager-1 3 }

Polaris-SysDisp-SNMP-Stat-SNMP-Inf-Mng-1-Alive-NoACK-global OBJECT-TYPE
	SYNTAX      Integer32
	MAX-ACCESS  read-only
	STATUS      current
	DESCRIPTION
		"<no units>"
        ::= { Polaris-SysDisp-SNMP-Stat-SNMP-Inf-Manager-1 4 }

Polaris-SysDisp-SNMP-Stat-SNMP-Inf-Mng-1-Alive-NoACK-local OBJECT-TYPE
	SYNTAX      Integer32
	MAX-ACCESS  read-only
	STATUS      current
	DESCRIPTION
		"<no units>"
        ::= { Polaris-SysDisp-SNMP-Stat-SNMP-Inf-Manager-1 5 }

Polaris-SysDisp-SNMP-Stat-SNMP-Inf-Mng-1-Value-Total-Created OBJECT-TYPE
	SYNTAX      Integer32
	MAX-ACCESS  read-only
	STATUS      current
	DESCRIPTION
		"<no units>"
        ::= { Polaris-SysDisp-SNMP-Stat-SNMP-Inf-Manager-1 6 }

Polaris-SysDisp-SNMP-Stat-SNMP-Inf-Mng-1-Value-REQ OBJECT-TYPE
	SYNTAX      Integer32
	MAX-ACCESS  read-only
	STATUS      current
	DESCRIPTION
		"<no units>"
        ::= { Polaris-SysDisp-SNMP-Stat-SNMP-Inf-Manager-1 7 }

Polaris-SysDisp-SNMP-Stat-SNMP-Inf-Mng-1-Value-ACK OBJECT-TYPE
	SYNTAX      Integer32
	MAX-ACCESS  read-only
	STATUS      current
	DESCRIPTION
		"<no units>"
        ::= { Polaris-SysDisp-SNMP-Stat-SNMP-Inf-Manager-1 8 }

Polaris-SysDisp-SNMP-Stat-SNMP-Inf-Mng-1-Value-NoACK-global OBJECT-TYPE
	SYNTAX      Integer32
	MAX-ACCESS  read-only
	STATUS      current
	DESCRIPTION
		"<no units>"
        ::= { Polaris-SysDisp-SNMP-Stat-SNMP-Inf-Manager-1 9 }

Polaris-SysDisp-SNMP-Stat-SNMP-Inf-Mng-1-Value-NoACK-local OBJECT-TYPE
	SYNTAX      Integer32
	MAX-ACCESS  read-only
	STATUS      current
	DESCRIPTION
		"<no units>"
        ::= { Polaris-SysDisp-SNMP-Stat-SNMP-Inf-Manager-1 10 }

Polaris-SysDisp-SNMP-Stat-SNMP-Inf-Mng-1-Value-FIFO-Load-Percent OBJECT-TYPE
	SYNTAX      Integer32
	MAX-ACCESS  read-only
	STATUS      current
	DESCRIPTION
		"% * 10"
        ::= { Polaris-SysDisp-SNMP-Stat-SNMP-Inf-Manager-1 11 }

Polaris-SysDisp-SNMP-Stat-SNMP-Inf-Mng-1-Value-FIFO-Load-Number OBJECT-TYPE
	SYNTAX      Integer32
	MAX-ACCESS  read-only
	STATUS      current
	DESCRIPTION
		"<no units>"
        ::= { Polaris-SysDisp-SNMP-Stat-SNMP-Inf-Manager-1 12 }

Polaris-SysDisp-SNMP-Stat-SNMP-Inf-Mng-1-Value-FIFO-Lost OBJECT-TYPE
	SYNTAX      Integer32
	MAX-ACCESS  read-only
	STATUS      current
	DESCRIPTION
		"<no units>"
        ::= { Polaris-SysDisp-SNMP-Stat-SNMP-Inf-Manager-1 13 }

Polaris-SysDisp-SNMP-Stat-SNMP-Inf-Mng-1-Message-Total-Created OBJECT-TYPE
	SYNTAX      Integer32
	MAX-ACCESS  read-only
	STATUS      current
	DESCRIPTION
		"<no units>"
        ::= { Polaris-SysDisp-SNMP-Stat-SNMP-Inf-Manager-1 14 }

Polaris-SysDisp-SNMP-Stat-SNMP-Inf-Mng-1-Message-REQ OBJECT-TYPE
	SYNTAX      Integer32
	MAX-ACCESS  read-only
	STATUS      current
	DESCRIPTION
		"<no units>"
        ::= { Polaris-SysDisp-SNMP-Stat-SNMP-Inf-Manager-1 15 }

Polaris-SysDisp-SNMP-Stat-SNMP-Inf-Mng-1-Message-ACK OBJECT-TYPE
	SYNTAX      Integer32
	MAX-ACCESS  read-only
	STATUS      current
	DESCRIPTION
		"<no units>"
        ::= { Polaris-SysDisp-SNMP-Stat-SNMP-Inf-Manager-1 16 }

Polaris-SysDisp-SNMP-Stat-SNMP-Inf-Mng-1-Message-NoACK-global OBJECT-TYPE
	SYNTAX      Integer32
	MAX-ACCESS  read-only
	STATUS      current
	DESCRIPTION
		"<no units>"
        ::= { Polaris-SysDisp-SNMP-Stat-SNMP-Inf-Manager-1 17 }

Polaris-SysDisp-SNMP-Stat-SNMP-Inf-Mng-1-Message-NoACK-local OBJECT-TYPE
	SYNTAX      Integer32
	MAX-ACCESS  read-only
	STATUS      current
	DESCRIPTION
		"<no units>"
        ::= { Polaris-SysDisp-SNMP-Stat-SNMP-Inf-Manager-1 18 }

Polaris-SysDisp-SNMP-Stat-SNMP-Inf-Mng-1-Message-FIFO-Load-Percent OBJECT-TYPE
	SYNTAX      Integer32
	MAX-ACCESS  read-only
	STATUS      current
	DESCRIPTION
		"% * 10"
        ::= { Polaris-SysDisp-SNMP-Stat-SNMP-Inf-Manager-1 19 }

Polaris-SysDisp-SNMP-Stat-SNMP-Inf-Mng-1-Message-FIFO-Load-Number OBJECT-TYPE
	SYNTAX      Integer32
	MAX-ACCESS  read-only
	STATUS      current
	DESCRIPTION
		"<no units>"
        ::= { Polaris-SysDisp-SNMP-Stat-SNMP-Inf-Manager-1 20 }

Polaris-SysDisp-SNMP-Stat-SNMP-Inf-Mng-1-Message-FIFO-Lost OBJECT-TYPE
	SYNTAX      Integer32
	MAX-ACCESS  read-only
	STATUS      current
	DESCRIPTION
		"<no units>"
        ::= { Polaris-SysDisp-SNMP-Stat-SNMP-Inf-Manager-1 21 }

Polaris-SysDisp-SNMP-Stat-SNMP-Inf-Mng-1-Status-Total-Created OBJECT-TYPE
	SYNTAX      Integer32
	MAX-ACCESS  read-only
	STATUS      current
	DESCRIPTION
		"<no units>"
        ::= { Polaris-SysDisp-SNMP-Stat-SNMP-Inf-Manager-1 22 }

Polaris-SysDisp-SNMP-Stat-SNMP-Inf-Mng-1-Status-REQ OBJECT-TYPE
	SYNTAX      Integer32
	MAX-ACCESS  read-only
	STATUS      current
	DESCRIPTION
		"<no units>"
        ::= { Polaris-SysDisp-SNMP-Stat-SNMP-Inf-Manager-1 23 }

Polaris-SysDisp-SNMP-Stat-SNMP-Inf-Mng-1-Status-ACK OBJECT-TYPE
	SYNTAX      Integer32
	MAX-ACCESS  read-only
	STATUS      current
	DESCRIPTION
		"<no units>"
        ::= { Polaris-SysDisp-SNMP-Stat-SNMP-Inf-Manager-1 24 }

Polaris-SysDisp-SNMP-Stat-SNMP-Inf-Mng-1-Status-NoACK-global OBJECT-TYPE
	SYNTAX      Integer32
	MAX-ACCESS  read-only
	STATUS      current
	DESCRIPTION
		"<no units>"
        ::= { Polaris-SysDisp-SNMP-Stat-SNMP-Inf-Manager-1 25 }

Polaris-SysDisp-SNMP-Stat-SNMP-Inf-Mng-1-Status-NoACK-local OBJECT-TYPE
	SYNTAX      Integer32
	MAX-ACCESS  read-only
	STATUS      current
	DESCRIPTION
		"<no units>"
        ::= { Polaris-SysDisp-SNMP-Stat-SNMP-Inf-Manager-1 26 }

Polaris-SysDisp-SNMP-Stat-SNMP-Inf-Mng-1-Status-Replaced OBJECT-TYPE
	SYNTAX      Integer32
	MAX-ACCESS  read-only
	STATUS      current
	DESCRIPTION
		"<no units>"
        ::= { Polaris-SysDisp-SNMP-Stat-SNMP-Inf-Manager-1 27 }

Polaris-SysDisp-SNMP-Main-Managers-Count OBJECT-TYPE
	SYNTAX      Integer32
	MAX-ACCESS  read-only
	STATUS      current
	DESCRIPTION
		"Total number of trap managers"
        ::= { Polaris-SysDisp-SNMP-Main 1 }

Polaris-SysDisp-DevType-Types-Count OBJECT-TYPE
	SYNTAX      Integer32
	MAX-ACCESS  read-only
	STATUS      current
	DESCRIPTION
		"<unused>"
        ::= { Polaris-SysDisp-Devices-Types 1 }

Polaris-SysDisp-DevType-Control-Units OBJECT-TYPE
	SYNTAX      Integer32
	MAX-ACCESS  read-only
	STATUS      current
	DESCRIPTION
		"1=Digital (supported), 2=Analog (not supported)"
        ::= { Polaris-SysDisp-Devices-Types 2 }

Polaris-SysDisp-DevType-Exciters OBJECT-TYPE
	SYNTAX      Integer32
	MAX-ACCESS  read-only
	STATUS      current
	DESCRIPTION
		"1=Digital (supported), 2=Analog (not supported)"
        ::= { Polaris-SysDisp-Devices-Types 3 }

Polaris-SysDisp-DevType-Amplifiers OBJECT-TYPE
	SYNTAX      Integer32
	MAX-ACCESS  read-only
	STATUS      current
	DESCRIPTION
		""
        ::= { Polaris-SysDisp-Devices-Types 4 }

Polaris-SysDisp-DevType-Ballasts OBJECT-TYPE
	SYNTAX      Integer32
	MAX-ACCESS  read-only
	STATUS      current
	DESCRIPTION
		""
        ::= { Polaris-SysDisp-Devices-Types 5 }

Polaris-SysDisp-DevType-Liquid-Coolers OBJECT-TYPE
	SYNTAX      Integer32
	MAX-ACCESS  read-only
	STATUS      current
	DESCRIPTION
		"<unused>"
        ::= { Polaris-SysDisp-Devices-Types 6 }

Polaris-SysDisp-DevType-Demodulators OBJECT-TYPE
	SYNTAX      Integer32
	MAX-ACCESS  read-only
	STATUS      current
	DESCRIPTION
		"<unused>"
        ::= { Polaris-SysDisp-Devices-Types 7 }

Polaris-SysDisp-DevType-Spare-Switch-Modules OBJECT-TYPE
	SYNTAX      Integer32
	MAX-ACCESS  read-only
	STATUS      current
	DESCRIPTION
		"<unused>"
        ::= { Polaris-SysDisp-Devices-Types 8 }

Polaris-SysDisp-DevType-Digital-Repeaters OBJECT-TYPE
	SYNTAX      Integer32
	MAX-ACCESS  read-only
	STATUS      current
	DESCRIPTION
		"<unused>"
        ::= { Polaris-SysDisp-Devices-Types 9 }

Polaris-SysDisp-DevType-SSM-2P1 OBJECT-TYPE
	SYNTAX      Integer32
	MAX-ACCESS  read-only
	STATUS      current
	DESCRIPTION
		"<unused>"
        ::= { Polaris-SysDisp-Devices-Types 20 }

Polaris-SysDisp-Pars-Average-Temperature OBJECT-TYPE
	SYNTAX      Integer32
	MAX-ACCESS  read-only
	STATUS      current
	DESCRIPTION
		"<unused>"
        ::= { Polaris-SysDisp-Pars 1 }

Polaris-SysDisp-Pars-Average-Temperature-Status OBJECT-TYPE
	SYNTAX      Integer32
	MAX-ACCESS  read-only
	STATUS      current
	DESCRIPTION
		"<unused>"
        ::= { Polaris-SysDisp-Pars 2 }

Polaris-SysDisp-Pars-Max-Temperature OBJECT-TYPE
	SYNTAX      Integer32
	MAX-ACCESS  read-only
	STATUS      current
	DESCRIPTION
		"<unused>"
        ::= { Polaris-SysDisp-Pars 3 }

Polaris-SysDisp-Pars-Max-Temperature-Status OBJECT-TYPE
	SYNTAX      Integer32
	MAX-ACCESS  read-only
	STATUS      current
	DESCRIPTION
		"<unused>"
        ::= { Polaris-SysDisp-Pars 4 }

Polaris-SysDisp-Pars-Currents-Units OBJECT-TYPE
	SYNTAX      INTEGER {unused (0), amper (1), percent (2)}
	MAX-ACCESS  read-only
	STATUS      current
	DESCRIPTION
		""
        ::= { Polaris-SysDisp-Pars 5 }

Polaris-SysDisp-RCS-Config-Revision OBJECT-TYPE
	SYNTAX      OCTET STRING
	MAX-ACCESS  read-only
	STATUS      current
	DESCRIPTION
		"<unused>"
        ::= { Polaris-SysDisp-RCS 1 }

Polaris-SysDisp-RCS-Software-Version OBJECT-TYPE
	SYNTAX      OCTET STRING
	MAX-ACCESS  read-only
	STATUS      current
	DESCRIPTION
		""
        ::= { Polaris-SysDisp-RCS 2 }

Polaris-SysDisp-RCS-SNMP-Version OBJECT-TYPE
	SYNTAX      INTEGER {ver1 (0), ver2 (1), ver3 (2)}
	MAX-ACCESS  read-only
	STATUS      current
	DESCRIPTION
		"<unused>"
        ::= { Polaris-SysDisp-RCS 3 }

Polaris-SysDisp-RCS-SNMP-MaxSize OBJECT-TYPE
	SYNTAX      Integer32
	MAX-ACCESS  read-only
	STATUS      current
	DESCRIPTION
		"<unused>"
        ::= { Polaris-SysDisp-RCS 4 }

Polaris-SysDisp-RCS-SNMP-MaxObjRate OBJECT-TYPE
	SYNTAX      Integer32
	MAX-ACCESS  read-only
	STATUS      current
	DESCRIPTION
		"<unused>"
        ::= { Polaris-SysDisp-RCS 5 }

Polaris-SysDisp-RCS-SNMP-Codepage OBJECT-TYPE
	SYNTAX      Integer32
	MAX-ACCESS  read-only
	STATUS      current
	DESCRIPTION
		"<unused>"
        ::= { Polaris-SysDisp-RCS 6 }

Polaris-SysDisp-RCS-Status OBJECT-TYPE
	SYNTAX      OCTET STRING
	MAX-ACCESS  read-only
	STATUS      current
	DESCRIPTION
		""
        ::= { Polaris-SysDisp-RCS 8 }

Polaris-SysDisp-RCS-Max-Post-Writes OBJECT-TYPE
	SYNTAX      Integer32
	MAX-ACCESS  read-only
	STATUS      current
	DESCRIPTION
		"<unused>"
        ::= { Polaris-SysDisp-RCS 10 }

Polaris-SysDisp-RCS-Informs-Queue-Wait OBJECT-TYPE
	SYNTAX      Integer32
	MAX-ACCESS  read-only
	STATUS      current
	DESCRIPTION
		"<unused>"
        ::= { Polaris-SysDisp-RCS 11 }

Polaris-SysDisp-RCS-Informs-Queue-Lost OBJECT-TYPE
	SYNTAX      Integer32
	MAX-ACCESS  read-only
	STATUS      current
	DESCRIPTION
		"<unused>"
        ::= { Polaris-SysDisp-RCS 12 }

Polaris-SysDisp-RCS-Informs-Seq-Number OBJECT-TYPE
	SYNTAX      Integer32
	MAX-ACCESS  read-only
	STATUS      current
	DESCRIPTION
		"<unused>"
        ::= { Polaris-SysDisp-RCS 13 }

Polaris-SysDisp-RCS-Date-Time OBJECT-TYPE
	SYNTAX      OCTET STRING
	MAX-ACCESS  read-only
	STATUS      current
	DESCRIPTION
		""
        ::= { Polaris-SysDisp-RCS 14 }

Polaris-SysDisp-RCS-Support-Options OBJECT-TYPE
	SYNTAX      Integer32
	MAX-ACCESS  read-only
	STATUS      current
	DESCRIPTION
		"<unused>"
        ::= { Polaris-SysDisp-RCS 17 }

Polaris-SysDisp-RCS-Tcp-Tunnels-Range OBJECT-TYPE
	SYNTAX      OCTET STRING
	MAX-ACCESS  read-only
	STATUS      current
	DESCRIPTION
		"<unused>"
        ::= { Polaris-SysDisp-RCS 20 }

Polaris-SysDisp-RCS-Tcp-Tunnels-Base OBJECT-TYPE
	SYNTAX      Integer32
	MAX-ACCESS  read-only
	STATUS      current
	DESCRIPTION
		"<unused>"
        ::= { Polaris-SysDisp-RCS 21 }

Polaris-SysDisp-RCS-Tcp-Tunnels-Alive OBJECT-TYPE
	SYNTAX      Integer32
	MAX-ACCESS  read-only
	STATUS      current
	DESCRIPTION
		"<unused>"
        ::= { Polaris-SysDisp-RCS 22 }

Polaris-SysDisp-RCS-Uptime OBJECT-TYPE
	SYNTAX      DateAndTime
	MAX-ACCESS  read-only
	STATUS      current
	DESCRIPTION
		""
        ::= { Polaris-SysDisp-RCS 7 }

Polaris-SysDisp-RCS-Busy-Count OBJECT-TYPE
	SYNTAX      Integer32
	MAX-ACCESS  read-only
	STATUS      current
	DESCRIPTION
		""
        ::= { Polaris-SysDisp-RCS 9 }

Polaris-SysDisp-RCS-Support-Models OBJECT-TYPE
	SYNTAX      OCTET STRING
	MAX-ACCESS  read-only
	STATUS      current
	DESCRIPTION
		""
        ::= { Polaris-SysDisp-RCS 15 }

Polaris-SysDisp-RCS-Functions OBJECT-TYPE
	SYNTAX      INTEGER {none (0), antennaProtection (1), transmitterServices (2)}
	MAX-ACCESS  read-only
	STATUS      current
	DESCRIPTION
		""
        ::= { Polaris-SysDisp-RCS 16 }

Polaris-SysDisp-RCS-Models-Titles OBJECT-TYPE
	SYNTAX      OCTET STRING
	MAX-ACCESS  read-only
	STATUS      current
	DESCRIPTION
		""
        ::= { Polaris-SysDisp-RCS 18 }

Polaris-SysDisp-RCS-Models-Infos OBJECT-TYPE
	SYNTAX      OCTET STRING
	MAX-ACCESS  read-only
	STATUS      current
	DESCRIPTION
		""
        ::= { Polaris-SysDisp-RCS 19 }

Polaris-SysDisp-Dev-Types-Count OBJECT-TYPE
	SYNTAX      Integer32
	MAX-ACCESS  read-only
	STATUS      current
	DESCRIPTION
		"<unused>"
        ::= { Polaris-SysDisp-Devices 1 }

Polaris-SysDisp-Dev-Liquid-Coolers OBJECT-TYPE
	SYNTAX      Integer32
	MAX-ACCESS  read-only
	STATUS      current
	DESCRIPTION
		"<unused>"
        ::= { Polaris-SysDisp-Devices 6 }

Polaris-SysDisp-Dev-Demodulators OBJECT-TYPE
	SYNTAX      Integer32
	MAX-ACCESS  read-only
	STATUS      current
	DESCRIPTION
		"<unused>"
        ::= { Polaris-SysDisp-Devices 7 }

Polaris-SysDisp-Dev-Spare-Switch-Modules OBJECT-TYPE
	SYNTAX      Integer32
	MAX-ACCESS  read-only
	STATUS      current
	DESCRIPTION
		"<unused>"
        ::= { Polaris-SysDisp-Devices 8 }

Polaris-SysDisp-Dev-Digital-Repeaters OBJECT-TYPE
	SYNTAX      Integer32
	MAX-ACCESS  read-only
	STATUS      current
	DESCRIPTION
		"<unused>"
        ::= { Polaris-SysDisp-Devices 9 }

Polaris-SysDisp-Dev-Control-Units OBJECT-TYPE
	SYNTAX      Integer32
	MAX-ACCESS  read-only
	STATUS      current
	DESCRIPTION
		""
        ::= { Polaris-SysDisp-Devices 2 }

Polaris-SysDisp-Dev-Exciters OBJECT-TYPE
	SYNTAX      Integer32
	MAX-ACCESS  read-only
	STATUS      current
	DESCRIPTION
		""
        ::= { Polaris-SysDisp-Devices 3 }

Polaris-SysDisp-Dev-Amplifiers OBJECT-TYPE
	SYNTAX      Integer32
	MAX-ACCESS  read-only
	STATUS      current
	DESCRIPTION
		""
        ::= { Polaris-SysDisp-Devices 4 }

Polaris-SysDisp-Dev-Ballasts OBJECT-TYPE
	SYNTAX      Integer32
	MAX-ACCESS  read-only
	STATUS      current
	DESCRIPTION
		""
        ::= { Polaris-SysDisp-Devices 5 }

Polaris-SysDisp-Dev-SSM-2P1 OBJECT-TYPE
	SYNTAX      Integer32
	MAX-ACCESS  read-only
	STATUS      current
	DESCRIPTION
		""
        ::= { Polaris-SysDisp-Devices 20 }

Polaris-SysDisp-Powers-PowerOut-Units OBJECT-TYPE
	SYNTAX      INTEGER {notAvailable (0), watt (1), kilowatt (2), decibel (3), percent (4), unused (-1)}
	MAX-ACCESS  read-only
	STATUS      current
	DESCRIPTION
		""
        ::= { Polaris-SysDisp-Powers 3 }

Polaris-SysDisp-Powers-PowerRef-Units OBJECT-TYPE
	SYNTAX      INTEGER {notAvailable (0), watt (1), kilowatt (2), decibel (3), percent (4), unused (-1)}
	MAX-ACCESS  read-only
	STATUS      current
	DESCRIPTION
		""
        ::= { Polaris-SysDisp-Powers 6 }

Polaris-SysDisp-Powers-PowerBallast OBJECT-TYPE
	SYNTAX      Integer32
	MAX-ACCESS  read-only
	STATUS      current
	DESCRIPTION
		"<unused>"
        ::= { Polaris-SysDisp-Powers 7 }

Polaris-SysDisp-Powers-PowerBallast-Divider OBJECT-TYPE
	SYNTAX      Integer32
	MAX-ACCESS  read-only
	STATUS      current
	DESCRIPTION
		"<unused>"
        ::= { Polaris-SysDisp-Powers 8 }

Polaris-SysDisp-Powers-PowerBallast-Units OBJECT-TYPE
	SYNTAX      INTEGER {notAvailable (0), watt (1), kilowatt (2), decibel (3), percent (4), unused (-1)}
	MAX-ACCESS  read-only
	STATUS      current
	DESCRIPTION
		"<unused>"
        ::= { Polaris-SysDisp-Powers 9 }

Polaris-SysDisp-Powers-PowerOut OBJECT-TYPE
	SYNTAX      Integer32
	MAX-ACCESS  read-only
	STATUS      current
	DESCRIPTION
		""
        ::= { Polaris-SysDisp-Powers 1 }

Polaris-SysDisp-Powers-PowerOut-Divider OBJECT-TYPE
	SYNTAX      Integer32
	MAX-ACCESS  read-only
	STATUS      current
	DESCRIPTION
		""
        ::= { Polaris-SysDisp-Powers 2 }

Polaris-SysDisp-Powers-PowerRef OBJECT-TYPE
	SYNTAX      Integer32
	MAX-ACCESS  read-only
	STATUS      current
	DESCRIPTION
		""
        ::= { Polaris-SysDisp-Powers 4 }

Polaris-SysDisp-Powers-PowerRef-Divider OBJECT-TYPE
	SYNTAX      Integer32
	MAX-ACCESS  read-only
	STATUS      current
	DESCRIPTION
		""
        ::= { Polaris-SysDisp-Powers 5 }

Polaris-SysDisp-Main-Global-Root-OID OBJECT-TYPE
	SYNTAX      OBJECT IDENTIFIER
	MAX-ACCESS  read-only
	STATUS      current
	DESCRIPTION
		"Transmitter's Global Root OID"
        ::= { Polaris-SysDisp-Main 1 }

Polaris-SysDisp-Main-Model-Root-OID OBJECT-TYPE
	SYNTAX      OBJECT IDENTIFIER
	MAX-ACCESS  read-only
	STATUS      current
	DESCRIPTION
		"Transmitter's Model Root OID"
        ::= { Polaris-SysDisp-Main 2 }

Polaris-SysDisp-Main-Model-Code OBJECT-TYPE
	SYNTAX      OCTET STRING
	MAX-ACCESS  read-only
	STATUS      current
	DESCRIPTION
		"Transmitter's Model Code"
        ::= { Polaris-SysDisp-Main 3 }

Polaris-SysDisp-Main-Model-Short OBJECT-TYPE
	SYNTAX      OCTET STRING
	MAX-ACCESS  read-only
	STATUS      current
	DESCRIPTION
		"Transmitter's Short Model (UTF8)"
        ::= { Polaris-SysDisp-Main 4 }

Polaris-SysDisp-Main-Model-Full OBJECT-TYPE
	SYNTAX      OCTET STRING
	MAX-ACCESS  read-only
	STATUS      current
	DESCRIPTION
		"Transmitter's Full Model (UTF8)"
        ::= { Polaris-SysDisp-Main 5 }

Polaris-SysDisp-Main-Model-Name OBJECT-TYPE
	SYNTAX      OCTET STRING
	MAX-ACCESS  read-only
	STATUS      current
	DESCRIPTION
		"Transmitter's Name/Location (UTF8)"
        ::= { Polaris-SysDisp-Main 6 }

Polaris-SysDisp-Main-Model-SerialNumber OBJECT-TYPE
	SYNTAX      Integer32
	MAX-ACCESS  read-only
	STATUS      current
	DESCRIPTION
		"Transmitter's Serial Number (0 - Disabled)"
        ::= { Polaris-SysDisp-Main 7 }

Polaris-SysDisp-Main-Model-Channel OBJECT-TYPE
	SYNTAX      Integer32
	MAX-ACCESS  read-only
	STATUS      current
	DESCRIPTION
		"Transmitter's Channel"
        ::= { Polaris-SysDisp-Main 8 }

Polaris-SysDisp-Main-Nominal-PowerOut-Watt OBJECT-TYPE
	SYNTAX      Integer32
	MAX-ACCESS  read-only
	STATUS      current
	DESCRIPTION
		"Transmitter's Typical PowerOut (Unit: 1 W)"
        ::= { Polaris-SysDisp-Main 9 }

Polaris-SysDisp-Main-Devices-Total-Count OBJECT-TYPE
	SYNTAX      Integer32
	MAX-ACCESS  read-only
	STATUS      current
	DESCRIPTION
		"Total Physical Devices in Transmitter"
        ::= { Polaris-SysDisp-Main 10 }

Polaris-SysDisp-Main-Devices-Connected-Count OBJECT-TYPE
	SYNTAX      Integer32
	MAX-ACCESS  read-only
	STATUS      current
	DESCRIPTION
		"Connected Physical Devices in Transmitter"
        ::= { Polaris-SysDisp-Main 11 }

Polaris-SysDisp-Main-Status-Warning OBJECT-TYPE
	SYNTAX      INTEGER {false(0), true(1)}
	MAX-ACCESS  read-only
	STATUS      current
	DESCRIPTION
		"Transmitter's Warning Status"
        ::= { Polaris-SysDisp-Main 12 }

Polaris-SysDisp-Main-Status-Failure OBJECT-TYPE
	SYNTAX      INTEGER {false(0), true(1)}
	MAX-ACCESS  read-only
	STATUS      current
	DESCRIPTION
		"Transmitter's Failure Status"
        ::= { Polaris-SysDisp-Main 13 }

Polaris-SysDisp-Main-SNMP-Device-ID OBJECT-TYPE
	SYNTAX      Integer32
	MAX-ACCESS  read-only
	STATUS      current
	DESCRIPTION
		"ID for SNMP logging to central server"
        ::= { Polaris-SysDisp-Main 14 }

Polaris-SysDisp-Main-Device-Type-ID OBJECT-TYPE
	SYNTAX      Integer32
	MAX-ACCESS  read-only
	STATUS      current
	DESCRIPTION
		"ID of Model Type"
        ::= { Polaris-SysDisp-Main 15 }

Polaris-SysDisp-Main-Optional-Demodulator-OID OBJECT-TYPE
	SYNTAX      OBJECT IDENTIFIER
	MAX-ACCESS  read-only
	STATUS      current
	DESCRIPTION
		"<unused>"
        ::= { Polaris-SysDisp-Main 16 }

Polaris-SysDisp-Main-Devices-Ignored-Count OBJECT-TYPE
	SYNTAX      Integer32
	MAX-ACCESS  read-only
	STATUS      current
	DESCRIPTION
		""
        ::= { Polaris-SysDisp-Main 17 }

uniSysCtl-sysCtl-Feedback-Command OBJECT-TYPE
	SYNTAX      OCTET STRING
	MAX-ACCESS  read-write
	STATUS      current
	DESCRIPTION
		""
        ::= { uniSysCtl-sysCtl 3 }

uniSysCtl-Ignore-Control-Units OBJECT-TYPE
	SYNTAX      Integer32
	MAX-ACCESS  read-write
	STATUS      current
	DESCRIPTION
		""
        ::= { uniSysCtl-Ignore-Devices 2 }

uniSysCtl-Ignore-Exciters OBJECT-TYPE
	SYNTAX      Integer32
	MAX-ACCESS  read-write
	STATUS      current
	DESCRIPTION
		""
        ::= { uniSysCtl-Ignore-Devices 3 }

uniSysCtl-Ignore-Amplifiers OBJECT-TYPE
	SYNTAX      Integer32
	MAX-ACCESS  read-write
	STATUS      current
	DESCRIPTION
		""
        ::= { uniSysCtl-Ignore-Devices 4 }

uniSysCtl-Ignore-Ballasts OBJECT-TYPE
	SYNTAX      Integer32
	MAX-ACCESS  read-write
	STATUS      current
	DESCRIPTION
		""
        ::= { uniSysCtl-Ignore-Devices 5 }

uniSysCtl-Misc-Reboot-Server OBJECT-TYPE
	SYNTAX      Integer32
	MAX-ACCESS  read-write
	STATUS      current
	DESCRIPTION
		"<unused>"
        ::= { uniSysCtl-Misc 1 }

uniSysCtl-Misc-Date-Time OBJECT-TYPE
	SYNTAX      OCTET STRING
	MAX-ACCESS  read-write
	STATUS      current
	DESCRIPTION
		""
        ::= { uniSysCtl-Misc 2 }

uniSysCtl-Misc-Language OBJECT-TYPE
	SYNTAX      Integer32
	MAX-ACCESS  read-write
	STATUS      current
	DESCRIPTION
		"<unused>"
        ::= { uniSysCtl-Misc 3 }

uniSysCtl-Misc-Restart-Agent OBJECT-TYPE
	SYNTAX      Integer32
	MAX-ACCESS  read-write
	STATUS      current
	DESCRIPTION
		""
        ::= { uniSysCtl-Misc 4 }

uniSysCtl-Misc-Drop-Devices OBJECT-TYPE
	SYNTAX      Integer32
	MAX-ACCESS  read-write
	STATUS      current
	DESCRIPTION
		"<unused>"
        ::= { uniSysCtl-Misc 5 }

uniSysCtl-Misc-Reset-Config OBJECT-TYPE
	SYNTAX      Integer32
	MAX-ACCESS  read-write
	STATUS      current
	DESCRIPTION
		"<unused>"
        ::= { uniSysCtl-Misc 6 }

uniSysCtl-RCS-Model-Code OBJECT-TYPE
	SYNTAX      OCTET STRING
	MAX-ACCESS  read-write
	STATUS      current
	DESCRIPTION
		""
        ::= { uniSysCtl-RCS 2 }

uniSysCtl-RCS-Model-Options OBJECT-TYPE
	SYNTAX      Integer32
	MAX-ACCESS  read-write
	STATUS      current
	DESCRIPTION
		""
        ::= { uniSysCtl-RCS 3 }

uniSysCtl-RCS-Model-Channel OBJECT-TYPE
	SYNTAX      Integer32
	MAX-ACCESS  read-only
	STATUS      current
	DESCRIPTION
		""
        ::= { uniSysCtl-RCS 4 }

uniSysCtl-RCS-Model-Serial-Number OBJECT-TYPE
	SYNTAX      Integer32
	MAX-ACCESS  read-write
	STATUS      current
	DESCRIPTION
		""
        ::= { uniSysCtl-RCS 5 }

uniSysCtl-RCS-Model-Name OBJECT-TYPE
	SYNTAX      OCTET STRING
	MAX-ACCESS  read-write
	STATUS      current
	DESCRIPTION
		""
        ::= { uniSysCtl-RCS 6 }

uniSysCtl-RCS-Base-IP OBJECT-TYPE
	SYNTAX      IPAddress
	MAX-ACCESS  read-write
	STATUS      current
	DESCRIPTION
		""
        ::= { uniSysCtl-RCS 7 }

uniSysCtl-RCS-Base-Port OBJECT-TYPE
	SYNTAX      Integer32
	MAX-ACCESS  read-write
	STATUS      current
	DESCRIPTION
		""
        ::= { uniSysCtl-RCS 8 }

uniSysCtl-RCS-Ports-Mapping OBJECT-TYPE
	SYNTAX      Integer32
	MAX-ACCESS  read-write
	STATUS      current
	DESCRIPTION
		"<unused>"
        ::= { uniSysCtl-RCS 9 }

uniSysCtl-RCS-SCPI-Port OBJECT-TYPE
	SYNTAX      Integer32
	MAX-ACCESS  read-write
	STATUS      current
	DESCRIPTION
		"<unused>"
        ::= { uniSysCtl-RCS 10 }

uniSysCtl-RCS-Use-TCP-Tunnels OBJECT-TYPE
	SYNTAX      Integer32
	MAX-ACCESS  read-write
	STATUS      current
	DESCRIPTION
		"<unused>"
        ::= { uniSysCtl-RCS 11 }

uniSysCtl-RCS-Aux-ID1 OBJECT-TYPE
	SYNTAX      Integer32
	MAX-ACCESS  read-write
	STATUS      current
	DESCRIPTION
		"<unused>"
        ::= { uniSysCtl-RCS 12 }

uniSysCtl-RCS-Aux-ID2 OBJECT-TYPE
	SYNTAX      Integer32
	MAX-ACCESS  read-write
	STATUS      current
	DESCRIPTION
		"<unused>"
        ::= { uniSysCtl-RCS 13 }

uniSysCtl-RCS-Exciters-Base-IP OBJECT-TYPE
	SYNTAX      IPAddress
	MAX-ACCESS  read-write
	STATUS      current
	DESCRIPTION
		"<unused>"
        ::= { uniSysCtl-RCS 14 }

uniSysCtl-RCS-Robust-Connection OBJECT-TYPE
	SYNTAX      Integer32
	MAX-ACCESS  read-write
	STATUS      current
	DESCRIPTION
		"<unused>"
        ::= { uniSysCtl-RCS 15 }

uniSysCtl-SNMPMisc-Send-Comment OBJECT-TYPE
	SYNTAX      OCTET STRING
	MAX-ACCESS  read-write
	STATUS      current
	DESCRIPTION
		""
        ::= { uniSysCtl-SNMP-Misc 1 }

uniSysCtl-SNMPMisc-Web-Username OBJECT-TYPE
	SYNTAX      OCTET STRING
	MAX-ACCESS  read-write
	STATUS      current
	DESCRIPTION
		"length: 0..64 symbols"
        ::= { uniSysCtl-SNMP-Misc 2 }

uniSysCtl-SNMP-Other-Alive-Notifies-Type OBJECT-TYPE
	SYNTAX      INTEGER {disabled (0), trap (1), inform (2)}
	MAX-ACCESS  read-write
	STATUS      current
	DESCRIPTION
		""
        ::= { uniSysCtl-SNMP-Other-Settings 1 }

uniSysCtl-SNMP-Other-Value-Notifies-Type OBJECT-TYPE
	SYNTAX      INTEGER {disabled (0), traps (1), informs (2)}
	MAX-ACCESS  read-write
	STATUS      current
	DESCRIPTION
		""
        ::= { uniSysCtl-SNMP-Other-Settings 2 }

uniSysCtl-SNMP-Other-Alive-Notifies-Period OBJECT-TYPE
	SYNTAX      Integer32
	MAX-ACCESS  read-write
	STATUS      current
	DESCRIPTION
		"seconds, range: 30..3600"
        ::= { uniSysCtl-SNMP-Other-Settings 3 }

uniSysCtl-SNMP-Other-Value-Notifies-Period OBJECT-TYPE
	SYNTAX      Integer32
	MAX-ACCESS  read-write
	STATUS      current
	DESCRIPTION
		"minutes, range: 1..1440"
        ::= { uniSysCtl-SNMP-Other-Settings 4 }

uniSysCtl-SNMP-Other-Informs-ACK-Timeout OBJECT-TYPE
	SYNTAX      Integer32
	MAX-ACCESS  read-write
	STATUS      current
	DESCRIPTION
		"seconds, range: 10..60"
        ::= { uniSysCtl-SNMP-Other-Settings 5 }

uniSysCtl-SNMP-Other-Message-Informs-Queue-Size OBJECT-TYPE
	SYNTAX      Integer32
	MAX-ACCESS  read-write
	STATUS      current
	DESCRIPTION
		"<no units>, range: 5..10000"
        ::= { uniSysCtl-SNMP-Other-Settings 6 }

uniSysCtl-SNMP-Other-Value-Informs-Queue-Size OBJECT-TYPE
	SYNTAX      Integer32
	MAX-ACCESS  read-write
	STATUS      current
	DESCRIPTION
		"<no units>, range: 5..10000"
        ::= { uniSysCtl-SNMP-Other-Settings 7 }

uniSysCtl-SNMP-Other-Status-Notifies-Type OBJECT-TYPE
	SYNTAX      INTEGER {false(0), true(1)}
	MAX-ACCESS  read-write
	STATUS      current
	DESCRIPTION
		""
        ::= { uniSysCtl-SNMP-Other-Settings 8 }

uniSysCtl-SNMP-Other-Status-Notifies-Period OBJECT-TYPE
	SYNTAX      Integer32
	MAX-ACCESS  read-write
	STATUS      current
	DESCRIPTION
		"minutes, range: 0..720, 0: disable periodical sending"
        ::= { uniSysCtl-SNMP-Other-Settings 9 }

uniSysCtl-SNMP-Other-Community-Get OBJECT-TYPE
	SYNTAX      OCTET STRING
	MAX-ACCESS  read-write
	STATUS      current
	DESCRIPTION
		"length: 1..32 symbols"
        ::= { uniSysCtl-SNMP-Other-Settings 10 }

uniSysCtl-SNMP-Other-Community-Set OBJECT-TYPE
	SYNTAX      OCTET STRING
	MAX-ACCESS  read-write
	STATUS      current
	DESCRIPTION
		"length: 1..32 symbols"
        ::= { uniSysCtl-SNMP-Other-Settings 11 }

uniSysCtl-SNMP-Other-Trusted-Network-1 OBJECT-TYPE
	SYNTAX      INTEGER {disabled (0), net_x_x_x_x (1), net_10_x_x_x (2), net_172_x_x_x (3), net_169_254_x_x (4), net_192_168_x_x (5), net_192_168_0_x (6), net_192_168_1_x (7), net_192_168_2_x (8), net_192_168_3_x (9), net_192_168_4_x (10), net_192_168_5_x (11), net_192_168_6_x (12), net_192_168_7_x (13)}
	MAX-ACCESS  read-write
	STATUS      current
	DESCRIPTION
		""
        ::= { uniSysCtl-SNMP-Other-Settings 12 }

uniSysCtl-SNMP-Other-Trusted-Network-2 OBJECT-TYPE
	SYNTAX      OCTET STRING
	MAX-ACCESS  read-write
	STATUS      current
	DESCRIPTION
		"string in CIDR-notation, 0.0.0.0/32 = disabled"
        ::= { uniSysCtl-SNMP-Other-Settings 13 }

uniSysCtl-SNMP-Other-Trusted-Network-3 OBJECT-TYPE
	SYNTAX      OCTET STRING
	MAX-ACCESS  read-write
	STATUS      current
	DESCRIPTION
		"string in CIDR-notation, 0.0.0.0/32 = disabled"
        ::= { uniSysCtl-SNMP-Other-Settings 14 }

uniSysCtl-SNMP-Other-Allow-Get OBJECT-TYPE
	SYNTAX      Integer32
	MAX-ACCESS  read-write
	STATUS      current
	DESCRIPTION
		"bits: 
0: Manager 1 
1: Manager 2 
2: Manager 3 
3: Manager 4 
4: Trusted Network 1 
5: Trusted Network 2 
6: Trusted Network 3 
7+: <UNUSED>, always=0"
        ::= { uniSysCtl-SNMP-Other-Settings 15 }

uniSysCtl-SNMP-Other-Allow-Set OBJECT-TYPE
	SYNTAX      Integer32
	MAX-ACCESS  read-write
	STATUS      current
	DESCRIPTION
		"bits: 
0: Manager 1 
1: Manager 2 
2: Manager 3 
3: Manager 4 
4: Trusted Network 1 
5: Trusted Network 2 
6: Trusted Network 3 
7+: <UNUSED>, always=0"
        ::= { uniSysCtl-SNMP-Other-Settings 16 }

uniSysCtl-SNMP-Other-Local-Logging OBJECT-TYPE
	SYNTAX      INTEGER {false(0), true(1)}
	MAX-ACCESS  read-write
	STATUS      current
	DESCRIPTION
		""
        ::= { uniSysCtl-SNMP-Other-Settings 17 }

uniSysCtl-SNMP-Managers-ID-1 OBJECT-TYPE
	SYNTAX      Integer32
	MAX-ACCESS  read-write
	STATUS      current
	DESCRIPTION
		"<no units>, range: 0..99999"
        ::= { uniSysCtl-SNMP-Managers-ID 1 }

uniSysCtl-SNMP-Managers-ID-2 OBJECT-TYPE
	SYNTAX      Integer32
	MAX-ACCESS  read-write
	STATUS      current
	DESCRIPTION
		"<no units>, range: 0..99999"
        ::= { uniSysCtl-SNMP-Managers-ID 2 }

uniSysCtl-SNMP-Managers-ID-3 OBJECT-TYPE
	SYNTAX      Integer32
	MAX-ACCESS  read-write
	STATUS      current
	DESCRIPTION
		"<no units>, range: 0..99999"
        ::= { uniSysCtl-SNMP-Managers-ID 3 }

uniSysCtl-SNMP-Managers-ID-4 OBJECT-TYPE
	SYNTAX      Integer32
	MAX-ACCESS  read-write
	STATUS      current
	DESCRIPTION
		"<no units>, range: 0..99999"
        ::= { uniSysCtl-SNMP-Managers-ID 4 }

uniSysCtl-SNMP-Managers-Community-1 OBJECT-TYPE
	SYNTAX      OCTET STRING
	MAX-ACCESS  read-write
	STATUS      current
	DESCRIPTION
		"length: 1..32 symbols"
        ::= { uniSysCtl-SNMP-Managers-Community 1 }

uniSysCtl-SNMP-Managers-Community-2 OBJECT-TYPE
	SYNTAX      OCTET STRING
	MAX-ACCESS  read-write
	STATUS      current
	DESCRIPTION
		"length: 1..32 symbols"
        ::= { uniSysCtl-SNMP-Managers-Community 2 }

uniSysCtl-SNMP-Managers-Community-3 OBJECT-TYPE
	SYNTAX      OCTET STRING
	MAX-ACCESS  read-write
	STATUS      current
	DESCRIPTION
		"length: 1..32 symbols"
        ::= { uniSysCtl-SNMP-Managers-Community 3 }

uniSysCtl-SNMP-Managers-Community-4 OBJECT-TYPE
	SYNTAX      OCTET STRING
	MAX-ACCESS  read-write
	STATUS      current
	DESCRIPTION
		"length: 1..32 symbols"
        ::= { uniSysCtl-SNMP-Managers-Community 4 }

uniSysCtl-SNMP-Managers-Port-1 OBJECT-TYPE
	SYNTAX      Integer32
	MAX-ACCESS  read-write
	STATUS      current
	DESCRIPTION
		"<no units>, range: 1..65535"
        ::= { uniSysCtl-SNMP-Managers-Port 1 }

uniSysCtl-SNMP-Managers-Port-2 OBJECT-TYPE
	SYNTAX      Integer32
	MAX-ACCESS  read-write
	STATUS      current
	DESCRIPTION
		"<no units>, range: 1..65535"
        ::= { uniSysCtl-SNMP-Managers-Port 2 }

uniSysCtl-SNMP-Managers-Port-3 OBJECT-TYPE
	SYNTAX      Integer32
	MAX-ACCESS  read-write
	STATUS      current
	DESCRIPTION
		"<no units>, range: 1..65535"
        ::= { uniSysCtl-SNMP-Managers-Port 3 }

uniSysCtl-SNMP-Managers-Port-4 OBJECT-TYPE
	SYNTAX      Integer32
	MAX-ACCESS  read-write
	STATUS      current
	DESCRIPTION
		"<no units>, range: 1..65535"
        ::= { uniSysCtl-SNMP-Managers-Port 4 }

uniSysCtl-SNMP-Managers-IP-1 OBJECT-TYPE
	SYNTAX      IPAddress
	MAX-ACCESS  read-write
	STATUS      current
	DESCRIPTION
		""
        ::= { uniSysCtl-SNMP-Managers-IP 1 }

uniSysCtl-SNMP-Managers-IP-2 OBJECT-TYPE
	SYNTAX      IPAddress
	MAX-ACCESS  read-write
	STATUS      current
	DESCRIPTION
		""
        ::= { uniSysCtl-SNMP-Managers-IP 2 }

uniSysCtl-SNMP-Managers-IP-3 OBJECT-TYPE
	SYNTAX      IPAddress
	MAX-ACCESS  read-write
	STATUS      current
	DESCRIPTION
		""
        ::= { uniSysCtl-SNMP-Managers-IP 3 }

uniSysCtl-SNMP-Managers-IP-4 OBJECT-TYPE
	SYNTAX      IPAddress
	MAX-ACCESS  read-write
	STATUS      current
	DESCRIPTION
		""
        ::= { uniSysCtl-SNMP-Managers-IP 4 }

uniSysDispTrans-Warning OBJECT-TYPE
	SYNTAX      INTEGER {false(0), true(1)}
	MAX-ACCESS  read-only
	STATUS      current
	DESCRIPTION
		""
        ::= { uniSysDisp-Transmitter 1 }

uniSysDispTrans-Failure OBJECT-TYPE
	SYNTAX      INTEGER {false(0), true(1)}
	MAX-ACCESS  read-only
	STATUS      current
	DESCRIPTION
		""
        ::= { uniSysDisp-Transmitter 2 }

uniSysDispTransRemoteLogState OBJECT-TYPE
	SYNTAX      INTEGER {notConnected (0), normal (1), warnings (2), failures (3)}
	MAX-ACCESS  read-only
	STATUS      current
	DESCRIPTION
		""
        ::= { uniSysDisp-Transmitter 10 }

uniSysDisp-SNMP-Stat-SNMP-Other-Last-Inform-ACK-Time OBJECT-TYPE
	SYNTAX      Integer32
	MAX-ACCESS  read-only
	STATUS      current
	DESCRIPTION
		"ms"
        ::= { uniSysDisp-SNMP-Stat-SNMP-Other 1 }

uniSysDisp-SNMP-Stat-SNMP-Other-Inform-ACK-Max-Time OBJECT-TYPE
	SYNTAX      Integer32
	MAX-ACCESS  read-only
	STATUS      current
	DESCRIPTION
		"ms"
        ::= { uniSysDisp-SNMP-Stat-SNMP-Other 2 }

uniSysDisp-SNMP-Stat-SNMP-Thread-Outcoming-Packets-Count OBJECT-TYPE
	SYNTAX      Integer32
	MAX-ACCESS  read-only
	STATUS      current
	DESCRIPTION
		""
        ::= { uniSysDisp-SNMP-Stat-SNMP-Thread-Monitoring 1 }

uniSysDisp-SNMP-Stat-SNMP-Thread-Unconfirmed-Messages-Count OBJECT-TYPE
	SYNTAX      Integer32
	MAX-ACCESS  read-only
	STATUS      current
	DESCRIPTION
		""
        ::= { uniSysDisp-SNMP-Stat-SNMP-Thread-Monitoring 2 }

uniSysDisp-SNMP-Stat-SNMP-Thread-Undelivered-Messages-Count OBJECT-TYPE
	SYNTAX      Integer32
	MAX-ACCESS  read-only
	STATUS      current
	DESCRIPTION
		""
        ::= { uniSysDisp-SNMP-Stat-SNMP-Thread-Monitoring 3 }

uniSysDisp-SNMP-Stat-Access-Err-Counter-Last-Access-Error-Text OBJECT-TYPE
	SYNTAX      OCTET STRING
	MAX-ACCESS  read-only
	STATUS      current
	DESCRIPTION
		""
        ::= { uniSysDisp-SNMP-Stat-Access-Errors-Counters 1 }

uniSysDisp-SNMP-Stat-Access-Err-Counter-Trap-V1 OBJECT-TYPE
	SYNTAX      Integer32
	MAX-ACCESS  read-only
	STATUS      current
	DESCRIPTION
		""
        ::= { uniSysDisp-SNMP-Stat-Access-Errors-Counters 2 }

uniSysDisp-SNMP-Stat-Access-Err-Counter-Trap-V2 OBJECT-TYPE
	SYNTAX      Integer32
	MAX-ACCESS  read-only
	STATUS      current
	DESCRIPTION
		""
        ::= { uniSysDisp-SNMP-Stat-Access-Errors-Counters 3 }

uniSysDisp-SNMP-Stat-Access-Err-Counter-Inform OBJECT-TYPE
	SYNTAX      Integer32
	MAX-ACCESS  read-only
	STATUS      current
	DESCRIPTION
		""
        ::= { uniSysDisp-SNMP-Stat-Access-Errors-Counters 4 }

uniSysDisp-SNMP-Stat-Access-Err-Counter-Get OBJECT-TYPE
	SYNTAX      Integer32
	MAX-ACCESS  read-only
	STATUS      current
	DESCRIPTION
		""
        ::= { uniSysDisp-SNMP-Stat-Access-Errors-Counters 5 }

uniSysDisp-SNMP-Stat-Access-Err-Counter-Get-Next OBJECT-TYPE
	SYNTAX      Integer32
	MAX-ACCESS  read-only
	STATUS      current
	DESCRIPTION
		""
        ::= { uniSysDisp-SNMP-Stat-Access-Errors-Counters 6 }

uniSysDisp-SNMP-Stat-Access-Err-Counter-Get-Bulk OBJECT-TYPE
	SYNTAX      Integer32
	MAX-ACCESS  read-only
	STATUS      current
	DESCRIPTION
		""
        ::= { uniSysDisp-SNMP-Stat-Access-Errors-Counters 7 }

uniSysDisp-SNMP-Stat-Access-Err-Counter-Set OBJECT-TYPE
	SYNTAX      Integer32
	MAX-ACCESS  read-only
	STATUS      current
	DESCRIPTION
		""
        ::= { uniSysDisp-SNMP-Stat-Access-Errors-Counters 8 }

uniSysDisp-SNMP-Stat-SNMP-Inf-Mng-4-Alive-Total-Created OBJECT-TYPE
	SYNTAX      Integer32
	MAX-ACCESS  read-only
	STATUS      current
	DESCRIPTION
		"<no units>"
        ::= { uniSysDisp-SNMP-Stat-SNMP-Inf-Manager-4 1 }

uniSysDisp-SNMP-Stat-SNMP-Inf-Mng-4-Alive-REQ OBJECT-TYPE
	SYNTAX      Integer32
	MAX-ACCESS  read-only
	STATUS      current
	DESCRIPTION
		"<no units>"
        ::= { uniSysDisp-SNMP-Stat-SNMP-Inf-Manager-4 2 }

uniSysDisp-SNMP-Stat-SNMP-Inf-Mng-4-Alive-ACK OBJECT-TYPE
	SYNTAX      Integer32
	MAX-ACCESS  read-only
	STATUS      current
	DESCRIPTION
		"<no units>"
        ::= { uniSysDisp-SNMP-Stat-SNMP-Inf-Manager-4 3 }

uniSysDisp-SNMP-Stat-SNMP-Inf-Mng-4-Alive-NoACK-global OBJECT-TYPE
	SYNTAX      Integer32
	MAX-ACCESS  read-only
	STATUS      current
	DESCRIPTION
		"<no units>"
        ::= { uniSysDisp-SNMP-Stat-SNMP-Inf-Manager-4 4 }

uniSysDisp-SNMP-Stat-SNMP-Inf-Mng-4-Alive-NoACK-local OBJECT-TYPE
	SYNTAX      Integer32
	MAX-ACCESS  read-only
	STATUS      current
	DESCRIPTION
		"<no units>"
        ::= { uniSysDisp-SNMP-Stat-SNMP-Inf-Manager-4 5 }

uniSysDisp-SNMP-Stat-SNMP-Inf-Mng-4-Value-Total-Created OBJECT-TYPE
	SYNTAX      Integer32
	MAX-ACCESS  read-only
	STATUS      current
	DESCRIPTION
		"<no units>"
        ::= { uniSysDisp-SNMP-Stat-SNMP-Inf-Manager-4 6 }

uniSysDisp-SNMP-Stat-SNMP-Inf-Mng-4-Value-REQ OBJECT-TYPE
	SYNTAX      Integer32
	MAX-ACCESS  read-only
	STATUS      current
	DESCRIPTION
		"<no units>"
        ::= { uniSysDisp-SNMP-Stat-SNMP-Inf-Manager-4 7 }

uniSysDisp-SNMP-Stat-SNMP-Inf-Mng-4-Value-ACK OBJECT-TYPE
	SYNTAX      Integer32
	MAX-ACCESS  read-only
	STATUS      current
	DESCRIPTION
		"<no units>"
        ::= { uniSysDisp-SNMP-Stat-SNMP-Inf-Manager-4 8 }

uniSysDisp-SNMP-Stat-SNMP-Inf-Mng-4-Value-NoACK-global OBJECT-TYPE
	SYNTAX      Integer32
	MAX-ACCESS  read-only
	STATUS      current
	DESCRIPTION
		"<no units>"
        ::= { uniSysDisp-SNMP-Stat-SNMP-Inf-Manager-4 9 }

uniSysDisp-SNMP-Stat-SNMP-Inf-Mng-4-Value-NoACK-local OBJECT-TYPE
	SYNTAX      Integer32
	MAX-ACCESS  read-only
	STATUS      current
	DESCRIPTION
		"<no units>"
        ::= { uniSysDisp-SNMP-Stat-SNMP-Inf-Manager-4 10 }

uniSysDisp-SNMP-Stat-SNMP-Inf-Mng-4-Value-FIFO-Load-Percent OBJECT-TYPE
	SYNTAX      Integer32
	MAX-ACCESS  read-only
	STATUS      current
	DESCRIPTION
		"% * 10"
        ::= { uniSysDisp-SNMP-Stat-SNMP-Inf-Manager-4 11 }

uniSysDisp-SNMP-Stat-SNMP-Inf-Mng-4-Value-FIFO-Load-Number OBJECT-TYPE
	SYNTAX      Integer32
	MAX-ACCESS  read-only
	STATUS      current
	DESCRIPTION
		"<no units>"
        ::= { uniSysDisp-SNMP-Stat-SNMP-Inf-Manager-4 12 }

uniSysDisp-SNMP-Stat-SNMP-Inf-Mng-4-Value-FIFO-Lost OBJECT-TYPE
	SYNTAX      Integer32
	MAX-ACCESS  read-only
	STATUS      current
	DESCRIPTION
		"<no units>"
        ::= { uniSysDisp-SNMP-Stat-SNMP-Inf-Manager-4 13 }

uniSysDisp-SNMP-Stat-SNMP-Inf-Mng-4-Message-Total-Created OBJECT-TYPE
	SYNTAX      Integer32
	MAX-ACCESS  read-only
	STATUS      current
	DESCRIPTION
		"<no units>"
        ::= { uniSysDisp-SNMP-Stat-SNMP-Inf-Manager-4 14 }

uniSysDisp-SNMP-Stat-SNMP-Inf-Mng-4-Message-REQ OBJECT-TYPE
	SYNTAX      Integer32
	MAX-ACCESS  read-only
	STATUS      current
	DESCRIPTION
		"<no units>"
        ::= { uniSysDisp-SNMP-Stat-SNMP-Inf-Manager-4 15 }

uniSysDisp-SNMP-Stat-SNMP-Inf-Mng-4-Message-ACK OBJECT-TYPE
	SYNTAX      Integer32
	MAX-ACCESS  read-only
	STATUS      current
	DESCRIPTION
		"<no units>"
        ::= { uniSysDisp-SNMP-Stat-SNMP-Inf-Manager-4 16 }

uniSysDisp-SNMP-Stat-SNMP-Inf-Mng-4-Message-NoACK-global OBJECT-TYPE
	SYNTAX      Integer32
	MAX-ACCESS  read-only
	STATUS      current
	DESCRIPTION
		"<no units>"
        ::= { uniSysDisp-SNMP-Stat-SNMP-Inf-Manager-4 17 }

uniSysDisp-SNMP-Stat-SNMP-Inf-Mng-4-Message-NoACK-local OBJECT-TYPE
	SYNTAX      Integer32
	MAX-ACCESS  read-only
	STATUS      current
	DESCRIPTION
		"<no units>"
        ::= { uniSysDisp-SNMP-Stat-SNMP-Inf-Manager-4 18 }

uniSysDisp-SNMP-Stat-SNMP-Inf-Mng-4-Message-FIFO-Load-Percent OBJECT-TYPE
	SYNTAX      Integer32
	MAX-ACCESS  read-only
	STATUS      current
	DESCRIPTION
		"% * 10"
        ::= { uniSysDisp-SNMP-Stat-SNMP-Inf-Manager-4 19 }

uniSysDisp-SNMP-Stat-SNMP-Inf-Mng-4-Message-FIFO-Load-Number OBJECT-TYPE
	SYNTAX      Integer32
	MAX-ACCESS  read-only
	STATUS      current
	DESCRIPTION
		"<no units>"
        ::= { uniSysDisp-SNMP-Stat-SNMP-Inf-Manager-4 20 }

uniSysDisp-SNMP-Stat-SNMP-Inf-Mng-4-Message-FIFO-Lost OBJECT-TYPE
	SYNTAX      Integer32
	MAX-ACCESS  read-only
	STATUS      current
	DESCRIPTION
		"<no units>"
        ::= { uniSysDisp-SNMP-Stat-SNMP-Inf-Manager-4 21 }

uniSysDisp-SNMP-Stat-SNMP-Inf-Mng-4-Status-Total-Created OBJECT-TYPE
	SYNTAX      Integer32
	MAX-ACCESS  read-only
	STATUS      current
	DESCRIPTION
		"<no units>"
        ::= { uniSysDisp-SNMP-Stat-SNMP-Inf-Manager-4 22 }

uniSysDisp-SNMP-Stat-SNMP-Inf-Mng-4-Status-REQ OBJECT-TYPE
	SYNTAX      Integer32
	MAX-ACCESS  read-only
	STATUS      current
	DESCRIPTION
		"<no units>"
        ::= { uniSysDisp-SNMP-Stat-SNMP-Inf-Manager-4 23 }

uniSysDisp-SNMP-Stat-SNMP-Inf-Mng-4-Status-ACK OBJECT-TYPE
	SYNTAX      Integer32
	MAX-ACCESS  read-only
	STATUS      current
	DESCRIPTION
		"<no units>"
        ::= { uniSysDisp-SNMP-Stat-SNMP-Inf-Manager-4 24 }

uniSysDisp-SNMP-Stat-SNMP-Inf-Mng-4-Status-NoACK-global OBJECT-TYPE
	SYNTAX      Integer32
	MAX-ACCESS  read-only
	STATUS      current
	DESCRIPTION
		"<no units>"
        ::= { uniSysDisp-SNMP-Stat-SNMP-Inf-Manager-4 25 }

uniSysDisp-SNMP-Stat-SNMP-Inf-Mng-4-Status-NoACK-local OBJECT-TYPE
	SYNTAX      Integer32
	MAX-ACCESS  read-only
	STATUS      current
	DESCRIPTION
		"<no units>"
        ::= { uniSysDisp-SNMP-Stat-SNMP-Inf-Manager-4 26 }

uniSysDisp-SNMP-Stat-SNMP-Inf-Mng-4-Status-Replaced OBJECT-TYPE
	SYNTAX      Integer32
	MAX-ACCESS  read-only
	STATUS      current
	DESCRIPTION
		"<no units>"
        ::= { uniSysDisp-SNMP-Stat-SNMP-Inf-Manager-4 27 }

uniSysDisp-SNMP-Stat-SNMP-Inf-Mng-3-Alive-Total-Created OBJECT-TYPE
	SYNTAX      Integer32
	MAX-ACCESS  read-only
	STATUS      current
	DESCRIPTION
		"<no units>"
        ::= { uniSysDisp-SNMP-Stat-SNMP-Inf-Manager-3 1 }

uniSysDisp-SNMP-Stat-SNMP-Inf-Mng-3-Alive-REQ OBJECT-TYPE
	SYNTAX      Integer32
	MAX-ACCESS  read-only
	STATUS      current
	DESCRIPTION
		"<no units>"
        ::= { uniSysDisp-SNMP-Stat-SNMP-Inf-Manager-3 2 }

uniSysDisp-SNMP-Stat-SNMP-Inf-Mng-3-Alive-ACK OBJECT-TYPE
	SYNTAX      Integer32
	MAX-ACCESS  read-only
	STATUS      current
	DESCRIPTION
		"<no units>"
        ::= { uniSysDisp-SNMP-Stat-SNMP-Inf-Manager-3 3 }

uniSysDisp-SNMP-Stat-SNMP-Inf-Mng-3-Alive-NoACK-global OBJECT-TYPE
	SYNTAX      Integer32
	MAX-ACCESS  read-only
	STATUS      current
	DESCRIPTION
		"<no units>"
        ::= { uniSysDisp-SNMP-Stat-SNMP-Inf-Manager-3 4 }

uniSysDisp-SNMP-Stat-SNMP-Inf-Mng-3-Alive-NoACK-local OBJECT-TYPE
	SYNTAX      Integer32
	MAX-ACCESS  read-only
	STATUS      current
	DESCRIPTION
		"<no units>"
        ::= { uniSysDisp-SNMP-Stat-SNMP-Inf-Manager-3 5 }

uniSysDisp-SNMP-Stat-SNMP-Inf-Mng-3-Value-Total-Created OBJECT-TYPE
	SYNTAX      Integer32
	MAX-ACCESS  read-only
	STATUS      current
	DESCRIPTION
		"<no units>"
        ::= { uniSysDisp-SNMP-Stat-SNMP-Inf-Manager-3 6 }

uniSysDisp-SNMP-Stat-SNMP-Inf-Mng-3-Value-REQ OBJECT-TYPE
	SYNTAX      Integer32
	MAX-ACCESS  read-only
	STATUS      current
	DESCRIPTION
		"<no units>"
        ::= { uniSysDisp-SNMP-Stat-SNMP-Inf-Manager-3 7 }

uniSysDisp-SNMP-Stat-SNMP-Inf-Mng-3-Value-ACK OBJECT-TYPE
	SYNTAX      Integer32
	MAX-ACCESS  read-only
	STATUS      current
	DESCRIPTION
		"<no units>"
        ::= { uniSysDisp-SNMP-Stat-SNMP-Inf-Manager-3 8 }

uniSysDisp-SNMP-Stat-SNMP-Inf-Mng-3-Value-NoACK-global OBJECT-TYPE
	SYNTAX      Integer32
	MAX-ACCESS  read-only
	STATUS      current
	DESCRIPTION
		"<no units>"
        ::= { uniSysDisp-SNMP-Stat-SNMP-Inf-Manager-3 9 }

uniSysDisp-SNMP-Stat-SNMP-Inf-Mng-3-Value-NoACK-local OBJECT-TYPE
	SYNTAX      Integer32
	MAX-ACCESS  read-only
	STATUS      current
	DESCRIPTION
		"<no units>"
        ::= { uniSysDisp-SNMP-Stat-SNMP-Inf-Manager-3 10 }

uniSysDisp-SNMP-Stat-SNMP-Inf-Mng-3-Value-FIFO-Load-Percent OBJECT-TYPE
	SYNTAX      Integer32
	MAX-ACCESS  read-only
	STATUS      current
	DESCRIPTION
		"% * 10"
        ::= { uniSysDisp-SNMP-Stat-SNMP-Inf-Manager-3 11 }

uniSysDisp-SNMP-Stat-SNMP-Inf-Mng-3-Value-FIFO-Load-Number OBJECT-TYPE
	SYNTAX      Integer32
	MAX-ACCESS  read-only
	STATUS      current
	DESCRIPTION
		"<no units>"
        ::= { uniSysDisp-SNMP-Stat-SNMP-Inf-Manager-3 12 }

uniSysDisp-SNMP-Stat-SNMP-Inf-Mng-3-Value-FIFO-Lost OBJECT-TYPE
	SYNTAX      Integer32
	MAX-ACCESS  read-only
	STATUS      current
	DESCRIPTION
		"<no units>"
        ::= { uniSysDisp-SNMP-Stat-SNMP-Inf-Manager-3 13 }

uniSysDisp-SNMP-Stat-SNMP-Inf-Mng-3-Message-Total-Created OBJECT-TYPE
	SYNTAX      Integer32
	MAX-ACCESS  read-only
	STATUS      current
	DESCRIPTION
		"<no units>"
        ::= { uniSysDisp-SNMP-Stat-SNMP-Inf-Manager-3 14 }

uniSysDisp-SNMP-Stat-SNMP-Inf-Mng-3-Message-REQ OBJECT-TYPE
	SYNTAX      Integer32
	MAX-ACCESS  read-only
	STATUS      current
	DESCRIPTION
		"<no units>"
        ::= { uniSysDisp-SNMP-Stat-SNMP-Inf-Manager-3 15 }

uniSysDisp-SNMP-Stat-SNMP-Inf-Mng-3-Message-ACK OBJECT-TYPE
	SYNTAX      Integer32
	MAX-ACCESS  read-only
	STATUS      current
	DESCRIPTION
		"<no units>"
        ::= { uniSysDisp-SNMP-Stat-SNMP-Inf-Manager-3 16 }

uniSysDisp-SNMP-Stat-SNMP-Inf-Mng-3-Message-NoACK-global OBJECT-TYPE
	SYNTAX      Integer32
	MAX-ACCESS  read-only
	STATUS      current
	DESCRIPTION
		"<no units>"
        ::= { uniSysDisp-SNMP-Stat-SNMP-Inf-Manager-3 17 }

uniSysDisp-SNMP-Stat-SNMP-Inf-Mng-3-Message-NoACK-local OBJECT-TYPE
	SYNTAX      Integer32
	MAX-ACCESS  read-only
	STATUS      current
	DESCRIPTION
		"<no units>"
        ::= { uniSysDisp-SNMP-Stat-SNMP-Inf-Manager-3 18 }

uniSysDisp-SNMP-Stat-SNMP-Inf-Mng-3-Message-FIFO-Load-Percent OBJECT-TYPE
	SYNTAX      Integer32
	MAX-ACCESS  read-only
	STATUS      current
	DESCRIPTION
		"% * 10"
        ::= { uniSysDisp-SNMP-Stat-SNMP-Inf-Manager-3 19 }

uniSysDisp-SNMP-Stat-SNMP-Inf-Mng-3-Message-FIFO-Load-Number OBJECT-TYPE
	SYNTAX      Integer32
	MAX-ACCESS  read-only
	STATUS      current
	DESCRIPTION
		"<no units>"
        ::= { uniSysDisp-SNMP-Stat-SNMP-Inf-Manager-3 20 }

uniSysDisp-SNMP-Stat-SNMP-Inf-Mng-3-Message-FIFO-Lost OBJECT-TYPE
	SYNTAX      Integer32
	MAX-ACCESS  read-only
	STATUS      current
	DESCRIPTION
		"<no units>"
        ::= { uniSysDisp-SNMP-Stat-SNMP-Inf-Manager-3 21 }

uniSysDisp-SNMP-Stat-SNMP-Inf-Mng-3-Status-Total-Created OBJECT-TYPE
	SYNTAX      Integer32
	MAX-ACCESS  read-only
	STATUS      current
	DESCRIPTION
		"<no units>"
        ::= { uniSysDisp-SNMP-Stat-SNMP-Inf-Manager-3 22 }

uniSysDisp-SNMP-Stat-SNMP-Inf-Mng-3-Status-REQ OBJECT-TYPE
	SYNTAX      Integer32
	MAX-ACCESS  read-only
	STATUS      current
	DESCRIPTION
		"<no units>"
        ::= { uniSysDisp-SNMP-Stat-SNMP-Inf-Manager-3 23 }

uniSysDisp-SNMP-Stat-SNMP-Inf-Mng-3-Status-ACK OBJECT-TYPE
	SYNTAX      Integer32
	MAX-ACCESS  read-only
	STATUS      current
	DESCRIPTION
		"<no units>"
        ::= { uniSysDisp-SNMP-Stat-SNMP-Inf-Manager-3 24 }

uniSysDisp-SNMP-Stat-SNMP-Inf-Mng-3-Status-NoACK-global OBJECT-TYPE
	SYNTAX      Integer32
	MAX-ACCESS  read-only
	STATUS      current
	DESCRIPTION
		"<no units>"
        ::= { uniSysDisp-SNMP-Stat-SNMP-Inf-Manager-3 25 }

uniSysDisp-SNMP-Stat-SNMP-Inf-Mng-3-Status-NoACK-local OBJECT-TYPE
	SYNTAX      Integer32
	MAX-ACCESS  read-only
	STATUS      current
	DESCRIPTION
		"<no units>"
        ::= { uniSysDisp-SNMP-Stat-SNMP-Inf-Manager-3 26 }

uniSysDisp-SNMP-Stat-SNMP-Inf-Mng-3-Status-Replaced OBJECT-TYPE
	SYNTAX      Integer32
	MAX-ACCESS  read-only
	STATUS      current
	DESCRIPTION
		"<no units>"
        ::= { uniSysDisp-SNMP-Stat-SNMP-Inf-Manager-3 27 }

uniSysDisp-SNMP-Stat-SNMP-Inf-Mng-2-Alive-Total-Created OBJECT-TYPE
	SYNTAX      Integer32
	MAX-ACCESS  read-only
	STATUS      current
	DESCRIPTION
		"<no units>"
        ::= { uniSysDisp-SNMP-Stat-SNMP-Inf-Manager-2 1 }

uniSysDisp-SNMP-Stat-SNMP-Inf-Mng-2-Alive-REQ OBJECT-TYPE
	SYNTAX      Integer32
	MAX-ACCESS  read-only
	STATUS      current
	DESCRIPTION
		"<no units>"
        ::= { uniSysDisp-SNMP-Stat-SNMP-Inf-Manager-2 2 }

uniSysDisp-SNMP-Stat-SNMP-Inf-Mng-2-Alive-ACK OBJECT-TYPE
	SYNTAX      Integer32
	MAX-ACCESS  read-only
	STATUS      current
	DESCRIPTION
		"<no units>"
        ::= { uniSysDisp-SNMP-Stat-SNMP-Inf-Manager-2 3 }

uniSysDisp-SNMP-Stat-SNMP-Inf-Mng-2-Alive-NoACK-global OBJECT-TYPE
	SYNTAX      Integer32
	MAX-ACCESS  read-only
	STATUS      current
	DESCRIPTION
		"<no units>"
        ::= { uniSysDisp-SNMP-Stat-SNMP-Inf-Manager-2 4 }

uniSysDisp-SNMP-Stat-SNMP-Inf-Mng-2-Alive-NoACK-local OBJECT-TYPE
	SYNTAX      Integer32
	MAX-ACCESS  read-only
	STATUS      current
	DESCRIPTION
		"<no units>"
        ::= { uniSysDisp-SNMP-Stat-SNMP-Inf-Manager-2 5 }

uniSysDisp-SNMP-Stat-SNMP-Inf-Mng-2-Value-Total-Created OBJECT-TYPE
	SYNTAX      Integer32
	MAX-ACCESS  read-only
	STATUS      current
	DESCRIPTION
		"<no units>"
        ::= { uniSysDisp-SNMP-Stat-SNMP-Inf-Manager-2 6 }

uniSysDisp-SNMP-Stat-SNMP-Inf-Mng-2-Value-REQ OBJECT-TYPE
	SYNTAX      Integer32
	MAX-ACCESS  read-only
	STATUS      current
	DESCRIPTION
		"<no units>"
        ::= { uniSysDisp-SNMP-Stat-SNMP-Inf-Manager-2 7 }

uniSysDisp-SNMP-Stat-SNMP-Inf-Mng-2-Value-ACK OBJECT-TYPE
	SYNTAX      Integer32
	MAX-ACCESS  read-only
	STATUS      current
	DESCRIPTION
		"<no units>"
        ::= { uniSysDisp-SNMP-Stat-SNMP-Inf-Manager-2 8 }

uniSysDisp-SNMP-Stat-SNMP-Inf-Mng-2-Value-NoACK-global OBJECT-TYPE
	SYNTAX      Integer32
	MAX-ACCESS  read-only
	STATUS      current
	DESCRIPTION
		"<no units>"
        ::= { uniSysDisp-SNMP-Stat-SNMP-Inf-Manager-2 9 }

uniSysDisp-SNMP-Stat-SNMP-Inf-Mng-2-Value-NoACK-local OBJECT-TYPE
	SYNTAX      Integer32
	MAX-ACCESS  read-only
	STATUS      current
	DESCRIPTION
		"<no units>"
        ::= { uniSysDisp-SNMP-Stat-SNMP-Inf-Manager-2 10 }

uniSysDisp-SNMP-Stat-SNMP-Inf-Mng-2-Value-FIFO-Load-Percent OBJECT-TYPE
	SYNTAX      Integer32
	MAX-ACCESS  read-only
	STATUS      current
	DESCRIPTION
		"% * 10"
        ::= { uniSysDisp-SNMP-Stat-SNMP-Inf-Manager-2 11 }

uniSysDisp-SNMP-Stat-SNMP-Inf-Mng-2-Value-FIFO-Load-Number OBJECT-TYPE
	SYNTAX      Integer32
	MAX-ACCESS  read-only
	STATUS      current
	DESCRIPTION
		"<no units>"
        ::= { uniSysDisp-SNMP-Stat-SNMP-Inf-Manager-2 12 }

uniSysDisp-SNMP-Stat-SNMP-Inf-Mng-2-Value-FIFO-Lost OBJECT-TYPE
	SYNTAX      Integer32
	MAX-ACCESS  read-only
	STATUS      current
	DESCRIPTION
		"<no units>"
        ::= { uniSysDisp-SNMP-Stat-SNMP-Inf-Manager-2 13 }

uniSysDisp-SNMP-Stat-SNMP-Inf-Mng-2-Message-Total-Created OBJECT-TYPE
	SYNTAX      Integer32
	MAX-ACCESS  read-only
	STATUS      current
	DESCRIPTION
		"<no units>"
        ::= { uniSysDisp-SNMP-Stat-SNMP-Inf-Manager-2 14 }

uniSysDisp-SNMP-Stat-SNMP-Inf-Mng-2-Message-REQ OBJECT-TYPE
	SYNTAX      Integer32
	MAX-ACCESS  read-only
	STATUS      current
	DESCRIPTION
		"<no units>"
        ::= { uniSysDisp-SNMP-Stat-SNMP-Inf-Manager-2 15 }

uniSysDisp-SNMP-Stat-SNMP-Inf-Mng-2-Message-ACK OBJECT-TYPE
	SYNTAX      Integer32
	MAX-ACCESS  read-only
	STATUS      current
	DESCRIPTION
		"<no units>"
        ::= { uniSysDisp-SNMP-Stat-SNMP-Inf-Manager-2 16 }

uniSysDisp-SNMP-Stat-SNMP-Inf-Mng-2-Message-NoACK-global OBJECT-TYPE
	SYNTAX      Integer32
	MAX-ACCESS  read-only
	STATUS      current
	DESCRIPTION
		"<no units>"
        ::= { uniSysDisp-SNMP-Stat-SNMP-Inf-Manager-2 17 }

uniSysDisp-SNMP-Stat-SNMP-Inf-Mng-2-Message-NoACK-local OBJECT-TYPE
	SYNTAX      Integer32
	MAX-ACCESS  read-only
	STATUS      current
	DESCRIPTION
		"<no units>"
        ::= { uniSysDisp-SNMP-Stat-SNMP-Inf-Manager-2 18 }

uniSysDisp-SNMP-Stat-SNMP-Inf-Mng-2-Message-FIFO-Load-Percent OBJECT-TYPE
	SYNTAX      Integer32
	MAX-ACCESS  read-only
	STATUS      current
	DESCRIPTION
		"% * 10"
        ::= { uniSysDisp-SNMP-Stat-SNMP-Inf-Manager-2 19 }

uniSysDisp-SNMP-Stat-SNMP-Inf-Mng-2-Message-FIFO-Load-Number OBJECT-TYPE
	SYNTAX      Integer32
	MAX-ACCESS  read-only
	STATUS      current
	DESCRIPTION
		"<no units>"
        ::= { uniSysDisp-SNMP-Stat-SNMP-Inf-Manager-2 20 }

uniSysDisp-SNMP-Stat-SNMP-Inf-Mng-2-Message-FIFO-Lost OBJECT-TYPE
	SYNTAX      Integer32
	MAX-ACCESS  read-only
	STATUS      current
	DESCRIPTION
		"<no units>"
        ::= { uniSysDisp-SNMP-Stat-SNMP-Inf-Manager-2 21 }

uniSysDisp-SNMP-Stat-SNMP-Inf-Mng-2-Status-Total-Created OBJECT-TYPE
	SYNTAX      Integer32
	MAX-ACCESS  read-only
	STATUS      current
	DESCRIPTION
		"<no units>"
        ::= { uniSysDisp-SNMP-Stat-SNMP-Inf-Manager-2 22 }

uniSysDisp-SNMP-Stat-SNMP-Inf-Mng-2-Status-REQ OBJECT-TYPE
	SYNTAX      Integer32
	MAX-ACCESS  read-only
	STATUS      current
	DESCRIPTION
		"<no units>"
        ::= { uniSysDisp-SNMP-Stat-SNMP-Inf-Manager-2 23 }

uniSysDisp-SNMP-Stat-SNMP-Inf-Mng-2-Status-ACK OBJECT-TYPE
	SYNTAX      Integer32
	MAX-ACCESS  read-only
	STATUS      current
	DESCRIPTION
		"<no units>"
        ::= { uniSysDisp-SNMP-Stat-SNMP-Inf-Manager-2 24 }

uniSysDisp-SNMP-Stat-SNMP-Inf-Mng-2-Status-NoACK-global OBJECT-TYPE
	SYNTAX      Integer32
	MAX-ACCESS  read-only
	STATUS      current
	DESCRIPTION
		"<no units>"
        ::= { uniSysDisp-SNMP-Stat-SNMP-Inf-Manager-2 25 }

uniSysDisp-SNMP-Stat-SNMP-Inf-Mng-2-Status-NoACK-local OBJECT-TYPE
	SYNTAX      Integer32
	MAX-ACCESS  read-only
	STATUS      current
	DESCRIPTION
		"<no units>"
        ::= { uniSysDisp-SNMP-Stat-SNMP-Inf-Manager-2 26 }

uniSysDisp-SNMP-Stat-SNMP-Inf-Mng-2-Status-Replaced OBJECT-TYPE
	SYNTAX      Integer32
	MAX-ACCESS  read-only
	STATUS      current
	DESCRIPTION
		"<no units>"
        ::= { uniSysDisp-SNMP-Stat-SNMP-Inf-Manager-2 27 }

uniSysDisp-SNMP-Stat-SNMP-Inf-Mng-1-Alive-Total-Created OBJECT-TYPE
	SYNTAX      Integer32
	MAX-ACCESS  read-only
	STATUS      current
	DESCRIPTION
		"<no units>"
        ::= { uniSysDisp-SNMP-Stat-SNMP-Inf-Manager-1 1 }

uniSysDisp-SNMP-Stat-SNMP-Inf-Mng-1-Alive-REQ OBJECT-TYPE
	SYNTAX      Integer32
	MAX-ACCESS  read-only
	STATUS      current
	DESCRIPTION
		"<no units>"
        ::= { uniSysDisp-SNMP-Stat-SNMP-Inf-Manager-1 2 }

uniSysDisp-SNMP-Stat-SNMP-Inf-Mng-1-Alive-ACK OBJECT-TYPE
	SYNTAX      Integer32
	MAX-ACCESS  read-only
	STATUS      current
	DESCRIPTION
		"<no units>"
        ::= { uniSysDisp-SNMP-Stat-SNMP-Inf-Manager-1 3 }

uniSysDisp-SNMP-Stat-SNMP-Inf-Mng-1-Alive-NoACK-global OBJECT-TYPE
	SYNTAX      Integer32
	MAX-ACCESS  read-only
	STATUS      current
	DESCRIPTION
		"<no units>"
        ::= { uniSysDisp-SNMP-Stat-SNMP-Inf-Manager-1 4 }

uniSysDisp-SNMP-Stat-SNMP-Inf-Mng-1-Alive-NoACK-local OBJECT-TYPE
	SYNTAX      Integer32
	MAX-ACCESS  read-only
	STATUS      current
	DESCRIPTION
		"<no units>"
        ::= { uniSysDisp-SNMP-Stat-SNMP-Inf-Manager-1 5 }

uniSysDisp-SNMP-Stat-SNMP-Inf-Mng-1-Value-Total-Created OBJECT-TYPE
	SYNTAX      Integer32
	MAX-ACCESS  read-only
	STATUS      current
	DESCRIPTION
		"<no units>"
        ::= { uniSysDisp-SNMP-Stat-SNMP-Inf-Manager-1 6 }

uniSysDisp-SNMP-Stat-SNMP-Inf-Mng-1-Value-REQ OBJECT-TYPE
	SYNTAX      Integer32
	MAX-ACCESS  read-only
	STATUS      current
	DESCRIPTION
		"<no units>"
        ::= { uniSysDisp-SNMP-Stat-SNMP-Inf-Manager-1 7 }

uniSysDisp-SNMP-Stat-SNMP-Inf-Mng-1-Value-ACK OBJECT-TYPE
	SYNTAX      Integer32
	MAX-ACCESS  read-only
	STATUS      current
	DESCRIPTION
		"<no units>"
        ::= { uniSysDisp-SNMP-Stat-SNMP-Inf-Manager-1 8 }

uniSysDisp-SNMP-Stat-SNMP-Inf-Mng-1-Value-NoACK-global OBJECT-TYPE
	SYNTAX      Integer32
	MAX-ACCESS  read-only
	STATUS      current
	DESCRIPTION
		"<no units>"
        ::= { uniSysDisp-SNMP-Stat-SNMP-Inf-Manager-1 9 }

uniSysDisp-SNMP-Stat-SNMP-Inf-Mng-1-Value-NoACK-local OBJECT-TYPE
	SYNTAX      Integer32
	MAX-ACCESS  read-only
	STATUS      current
	DESCRIPTION
		"<no units>"
        ::= { uniSysDisp-SNMP-Stat-SNMP-Inf-Manager-1 10 }

uniSysDisp-SNMP-Stat-SNMP-Inf-Mng-1-Value-FIFO-Load-Percent OBJECT-TYPE
	SYNTAX      Integer32
	MAX-ACCESS  read-only
	STATUS      current
	DESCRIPTION
		"% * 10"
        ::= { uniSysDisp-SNMP-Stat-SNMP-Inf-Manager-1 11 }

uniSysDisp-SNMP-Stat-SNMP-Inf-Mng-1-Value-FIFO-Load-Number OBJECT-TYPE
	SYNTAX      Integer32
	MAX-ACCESS  read-only
	STATUS      current
	DESCRIPTION
		"<no units>"
        ::= { uniSysDisp-SNMP-Stat-SNMP-Inf-Manager-1 12 }

uniSysDisp-SNMP-Stat-SNMP-Inf-Mng-1-Value-FIFO-Lost OBJECT-TYPE
	SYNTAX      Integer32
	MAX-ACCESS  read-only
	STATUS      current
	DESCRIPTION
		"<no units>"
        ::= { uniSysDisp-SNMP-Stat-SNMP-Inf-Manager-1 13 }

uniSysDisp-SNMP-Stat-SNMP-Inf-Mng-1-Message-Total-Created OBJECT-TYPE
	SYNTAX      Integer32
	MAX-ACCESS  read-only
	STATUS      current
	DESCRIPTION
		"<no units>"
        ::= { uniSysDisp-SNMP-Stat-SNMP-Inf-Manager-1 14 }

uniSysDisp-SNMP-Stat-SNMP-Inf-Mng-1-Message-REQ OBJECT-TYPE
	SYNTAX      Integer32
	MAX-ACCESS  read-only
	STATUS      current
	DESCRIPTION
		"<no units>"
        ::= { uniSysDisp-SNMP-Stat-SNMP-Inf-Manager-1 15 }

uniSysDisp-SNMP-Stat-SNMP-Inf-Mng-1-Message-ACK OBJECT-TYPE
	SYNTAX      Integer32
	MAX-ACCESS  read-only
	STATUS      current
	DESCRIPTION
		"<no units>"
        ::= { uniSysDisp-SNMP-Stat-SNMP-Inf-Manager-1 16 }

uniSysDisp-SNMP-Stat-SNMP-Inf-Mng-1-Message-NoACK-global OBJECT-TYPE
	SYNTAX      Integer32
	MAX-ACCESS  read-only
	STATUS      current
	DESCRIPTION
		"<no units>"
        ::= { uniSysDisp-SNMP-Stat-SNMP-Inf-Manager-1 17 }

uniSysDisp-SNMP-Stat-SNMP-Inf-Mng-1-Message-NoACK-local OBJECT-TYPE
	SYNTAX      Integer32
	MAX-ACCESS  read-only
	STATUS      current
	DESCRIPTION
		"<no units>"
        ::= { uniSysDisp-SNMP-Stat-SNMP-Inf-Manager-1 18 }

uniSysDisp-SNMP-Stat-SNMP-Inf-Mng-1-Message-FIFO-Load-Percent OBJECT-TYPE
	SYNTAX      Integer32
	MAX-ACCESS  read-only
	STATUS      current
	DESCRIPTION
		"% * 10"
        ::= { uniSysDisp-SNMP-Stat-SNMP-Inf-Manager-1 19 }

uniSysDisp-SNMP-Stat-SNMP-Inf-Mng-1-Message-FIFO-Load-Number OBJECT-TYPE
	SYNTAX      Integer32
	MAX-ACCESS  read-only
	STATUS      current
	DESCRIPTION
		"<no units>"
        ::= { uniSysDisp-SNMP-Stat-SNMP-Inf-Manager-1 20 }

uniSysDisp-SNMP-Stat-SNMP-Inf-Mng-1-Message-FIFO-Lost OBJECT-TYPE
	SYNTAX      Integer32
	MAX-ACCESS  read-only
	STATUS      current
	DESCRIPTION
		"<no units>"
        ::= { uniSysDisp-SNMP-Stat-SNMP-Inf-Manager-1 21 }

uniSysDisp-SNMP-Stat-SNMP-Inf-Mng-1-Status-Total-Created OBJECT-TYPE
	SYNTAX      Integer32
	MAX-ACCESS  read-only
	STATUS      current
	DESCRIPTION
		"<no units>"
        ::= { uniSysDisp-SNMP-Stat-SNMP-Inf-Manager-1 22 }

uniSysDisp-SNMP-Stat-SNMP-Inf-Mng-1-Status-REQ OBJECT-TYPE
	SYNTAX      Integer32
	MAX-ACCESS  read-only
	STATUS      current
	DESCRIPTION
		"<no units>"
        ::= { uniSysDisp-SNMP-Stat-SNMP-Inf-Manager-1 23 }

uniSysDisp-SNMP-Stat-SNMP-Inf-Mng-1-Status-ACK OBJECT-TYPE
	SYNTAX      Integer32
	MAX-ACCESS  read-only
	STATUS      current
	DESCRIPTION
		"<no units>"
        ::= { uniSysDisp-SNMP-Stat-SNMP-Inf-Manager-1 24 }

uniSysDisp-SNMP-Stat-SNMP-Inf-Mng-1-Status-NoACK-global OBJECT-TYPE
	SYNTAX      Integer32
	MAX-ACCESS  read-only
	STATUS      current
	DESCRIPTION
		"<no units>"
        ::= { uniSysDisp-SNMP-Stat-SNMP-Inf-Manager-1 25 }

uniSysDisp-SNMP-Stat-SNMP-Inf-Mng-1-Status-NoACK-local OBJECT-TYPE
	SYNTAX      Integer32
	MAX-ACCESS  read-only
	STATUS      current
	DESCRIPTION
		"<no units>"
        ::= { uniSysDisp-SNMP-Stat-SNMP-Inf-Manager-1 26 }

uniSysDisp-SNMP-Stat-SNMP-Inf-Mng-1-Status-Replaced OBJECT-TYPE
	SYNTAX      Integer32
	MAX-ACCESS  read-only
	STATUS      current
	DESCRIPTION
		"<no units>"
        ::= { uniSysDisp-SNMP-Stat-SNMP-Inf-Manager-1 27 }

uniSysDisp-SNMP-Main-Managers-Count OBJECT-TYPE
	SYNTAX      Integer32
	MAX-ACCESS  read-only
	STATUS      current
	DESCRIPTION
		"Total number of trap managers"
        ::= { uniSysDisp-SNMP-Main 1 }

uniSysDisp-DevType-Types-Count OBJECT-TYPE
	SYNTAX      Integer32
	MAX-ACCESS  read-only
	STATUS      current
	DESCRIPTION
		"<unused>"
        ::= { uniSysDisp-Devices-Types 1 }

uniSysDisp-DevType-Control-Units OBJECT-TYPE
	SYNTAX      Integer32
	MAX-ACCESS  read-only
	STATUS      current
	DESCRIPTION
		"1=Digital (supported), 2=Analog (not supported)"
        ::= { uniSysDisp-Devices-Types 2 }

uniSysDisp-DevType-Exciters OBJECT-TYPE
	SYNTAX      Integer32
	MAX-ACCESS  read-only
	STATUS      current
	DESCRIPTION
		"1=Digital (supported), 2=Analog (not supported)"
        ::= { uniSysDisp-Devices-Types 3 }

uniSysDisp-DevType-Amplifiers OBJECT-TYPE
	SYNTAX      Integer32
	MAX-ACCESS  read-only
	STATUS      current
	DESCRIPTION
		""
        ::= { uniSysDisp-Devices-Types 4 }

uniSysDisp-DevType-Ballasts OBJECT-TYPE
	SYNTAX      Integer32
	MAX-ACCESS  read-only
	STATUS      current
	DESCRIPTION
		""
        ::= { uniSysDisp-Devices-Types 5 }

uniSysDisp-DevType-Liquid-Coolers OBJECT-TYPE
	SYNTAX      Integer32
	MAX-ACCESS  read-only
	STATUS      current
	DESCRIPTION
		"<unused>"
        ::= { uniSysDisp-Devices-Types 6 }

uniSysDisp-DevType-Demodulators OBJECT-TYPE
	SYNTAX      Integer32
	MAX-ACCESS  read-only
	STATUS      current
	DESCRIPTION
		"<unused>"
        ::= { uniSysDisp-Devices-Types 7 }

uniSysDisp-DevType-Spare-Switch-Modules OBJECT-TYPE
	SYNTAX      Integer32
	MAX-ACCESS  read-only
	STATUS      current
	DESCRIPTION
		"<unused>"
        ::= { uniSysDisp-Devices-Types 8 }

uniSysDisp-DevType-Digital-Repeaters OBJECT-TYPE
	SYNTAX      Integer32
	MAX-ACCESS  read-only
	STATUS      current
	DESCRIPTION
		"<unused>"
        ::= { uniSysDisp-Devices-Types 9 }

uniSysDisp-DevType-SSM-2P1 OBJECT-TYPE
	SYNTAX      Integer32
	MAX-ACCESS  read-only
	STATUS      current
	DESCRIPTION
		"<unused>"
        ::= { uniSysDisp-Devices-Types 20 }

uniSysDisp-Pars-Average-Temperature OBJECT-TYPE
	SYNTAX      Integer32
	MAX-ACCESS  read-only
	STATUS      current
	DESCRIPTION
		"<unused>"
        ::= { uniSysDisp-Pars 1 }

uniSysDisp-Pars-Average-Temperature-Status OBJECT-TYPE
	SYNTAX      Integer32
	MAX-ACCESS  read-only
	STATUS      current
	DESCRIPTION
		"<unused>"
        ::= { uniSysDisp-Pars 2 }

uniSysDisp-Pars-Max-Temperature OBJECT-TYPE
	SYNTAX      Integer32
	MAX-ACCESS  read-only
	STATUS      current
	DESCRIPTION
		"<unused>"
        ::= { uniSysDisp-Pars 3 }

uniSysDisp-Pars-Max-Temperature-Status OBJECT-TYPE
	SYNTAX      Integer32
	MAX-ACCESS  read-only
	STATUS      current
	DESCRIPTION
		"<unused>"
        ::= { uniSysDisp-Pars 4 }

uniSysDisp-Pars-Currents-Units OBJECT-TYPE
	SYNTAX      INTEGER {unused (0), amper (1), percent (2)}
	MAX-ACCESS  read-only
	STATUS      current
	DESCRIPTION
		""
        ::= { uniSysDisp-Pars 5 }

uniSysDisp-RCS-Config-Revision OBJECT-TYPE
	SYNTAX      OCTET STRING
	MAX-ACCESS  read-only
	STATUS      current
	DESCRIPTION
		"<unused>"
        ::= { uniSysDisp-RCS 1 }

uniSysDisp-RCS-Software-Version OBJECT-TYPE
	SYNTAX      OCTET STRING
	MAX-ACCESS  read-only
	STATUS      current
	DESCRIPTION
		""
        ::= { uniSysDisp-RCS 2 }

uniSysDisp-RCS-SNMP-Version OBJECT-TYPE
	SYNTAX      INTEGER {ver1 (0), ver2 (1), ver3 (2)}
	MAX-ACCESS  read-only
	STATUS      current
	DESCRIPTION
		"<unused>"
        ::= { uniSysDisp-RCS 3 }

uniSysDisp-RCS-SNMP-MaxSize OBJECT-TYPE
	SYNTAX      Integer32
	MAX-ACCESS  read-only
	STATUS      current
	DESCRIPTION
		"<unused>"
        ::= { uniSysDisp-RCS 4 }

uniSysDisp-RCS-SNMP-MaxObjRate OBJECT-TYPE
	SYNTAX      Integer32
	MAX-ACCESS  read-only
	STATUS      current
	DESCRIPTION
		"<unused>"
        ::= { uniSysDisp-RCS 5 }

uniSysDisp-RCS-SNMP-Codepage OBJECT-TYPE
	SYNTAX      Integer32
	MAX-ACCESS  read-only
	STATUS      current
	DESCRIPTION
		"<unused>"
        ::= { uniSysDisp-RCS 6 }

uniSysDisp-RCS-Status OBJECT-TYPE
	SYNTAX      OCTET STRING
	MAX-ACCESS  read-only
	STATUS      current
	DESCRIPTION
		""
        ::= { uniSysDisp-RCS 8 }

uniSysDisp-RCS-Max-Post-Writes OBJECT-TYPE
	SYNTAX      Integer32
	MAX-ACCESS  read-only
	STATUS      current
	DESCRIPTION
		"<unused>"
        ::= { uniSysDisp-RCS 10 }

uniSysDisp-RCS-Informs-Queue-Wait OBJECT-TYPE
	SYNTAX      Integer32
	MAX-ACCESS  read-only
	STATUS      current
	DESCRIPTION
		"<unused>"
        ::= { uniSysDisp-RCS 11 }

uniSysDisp-RCS-Informs-Queue-Lost OBJECT-TYPE
	SYNTAX      Integer32
	MAX-ACCESS  read-only
	STATUS      current
	DESCRIPTION
		"<unused>"
        ::= { uniSysDisp-RCS 12 }

uniSysDisp-RCS-Informs-Seq-Number OBJECT-TYPE
	SYNTAX      Integer32
	MAX-ACCESS  read-only
	STATUS      current
	DESCRIPTION
		"<unused>"
        ::= { uniSysDisp-RCS 13 }

uniSysDisp-RCS-Date-Time OBJECT-TYPE
	SYNTAX      OCTET STRING
	MAX-ACCESS  read-only
	STATUS      current
	DESCRIPTION
		""
        ::= { uniSysDisp-RCS 14 }

uniSysDisp-RCS-Support-Options OBJECT-TYPE
	SYNTAX      Integer32
	MAX-ACCESS  read-only
	STATUS      current
	DESCRIPTION
		"<unused>"
        ::= { uniSysDisp-RCS 17 }

uniSysDisp-RCS-Tcp-Tunnels-Range OBJECT-TYPE
	SYNTAX      OCTET STRING
	MAX-ACCESS  read-only
	STATUS      current
	DESCRIPTION
		"<unused>"
        ::= { uniSysDisp-RCS 20 }

uniSysDisp-RCS-Tcp-Tunnels-Base OBJECT-TYPE
	SYNTAX      Integer32
	MAX-ACCESS  read-only
	STATUS      current
	DESCRIPTION
		"<unused>"
        ::= { uniSysDisp-RCS 21 }

uniSysDisp-RCS-Tcp-Tunnels-Alive OBJECT-TYPE
	SYNTAX      Integer32
	MAX-ACCESS  read-only
	STATUS      current
	DESCRIPTION
		"<unused>"
        ::= { uniSysDisp-RCS 22 }

uniSysDisp-RCS-Uptime OBJECT-TYPE
	SYNTAX      DateAndTime
	MAX-ACCESS  read-only
	STATUS      current
	DESCRIPTION
		""
        ::= { uniSysDisp-RCS 7 }

uniSysDisp-RCS-Busy-Count OBJECT-TYPE
	SYNTAX      Integer32
	MAX-ACCESS  read-only
	STATUS      current
	DESCRIPTION
		""
        ::= { uniSysDisp-RCS 9 }

uniSysDisp-RCS-Support-Models OBJECT-TYPE
	SYNTAX      OCTET STRING
	MAX-ACCESS  read-only
	STATUS      current
	DESCRIPTION
		""
        ::= { uniSysDisp-RCS 15 }

uniSysDisp-RCS-Functions OBJECT-TYPE
	SYNTAX      INTEGER {none (0), antennaProtection (1), transmitterServices (2)}
	MAX-ACCESS  read-only
	STATUS      current
	DESCRIPTION
		""
        ::= { uniSysDisp-RCS 16 }

uniSysDisp-RCS-Models-Titles OBJECT-TYPE
	SYNTAX      OCTET STRING
	MAX-ACCESS  read-only
	STATUS      current
	DESCRIPTION
		""
        ::= { uniSysDisp-RCS 18 }

uniSysDisp-RCS-Models-Infos OBJECT-TYPE
	SYNTAX      OCTET STRING
	MAX-ACCESS  read-only
	STATUS      current
	DESCRIPTION
		""
        ::= { uniSysDisp-RCS 19 }

uniSysDisp-Dev-Types-Count OBJECT-TYPE
	SYNTAX      Integer32
	MAX-ACCESS  read-only
	STATUS      current
	DESCRIPTION
		"<unused>"
        ::= { uniSysDisp-Devices 1 }

uniSysDisp-Dev-Liquid-Coolers OBJECT-TYPE
	SYNTAX      Integer32
	MAX-ACCESS  read-only
	STATUS      current
	DESCRIPTION
		"<unused>"
        ::= { uniSysDisp-Devices 6 }

uniSysDisp-Dev-Demodulators OBJECT-TYPE
	SYNTAX      Integer32
	MAX-ACCESS  read-only
	STATUS      current
	DESCRIPTION
		"<unused>"
        ::= { uniSysDisp-Devices 7 }

uniSysDisp-Dev-Spare-Switch-Modules OBJECT-TYPE
	SYNTAX      Integer32
	MAX-ACCESS  read-only
	STATUS      current
	DESCRIPTION
		"<unused>"
        ::= { uniSysDisp-Devices 8 }

uniSysDisp-Dev-Digital-Repeaters OBJECT-TYPE
	SYNTAX      Integer32
	MAX-ACCESS  read-only
	STATUS      current
	DESCRIPTION
		"<unused>"
        ::= { uniSysDisp-Devices 9 }

uniSysDisp-Dev-Control-Units OBJECT-TYPE
	SYNTAX      Integer32
	MAX-ACCESS  read-only
	STATUS      current
	DESCRIPTION
		""
        ::= { uniSysDisp-Devices 2 }

uniSysDisp-Dev-Exciters OBJECT-TYPE
	SYNTAX      Integer32
	MAX-ACCESS  read-only
	STATUS      current
	DESCRIPTION
		""
        ::= { uniSysDisp-Devices 3 }

uniSysDisp-Dev-Amplifiers OBJECT-TYPE
	SYNTAX      Integer32
	MAX-ACCESS  read-only
	STATUS      current
	DESCRIPTION
		""
        ::= { uniSysDisp-Devices 4 }

uniSysDisp-Dev-Ballasts OBJECT-TYPE
	SYNTAX      Integer32
	MAX-ACCESS  read-only
	STATUS      current
	DESCRIPTION
		""
        ::= { uniSysDisp-Devices 5 }

uniSysDisp-Dev-SSM-2P1 OBJECT-TYPE
	SYNTAX      Integer32
	MAX-ACCESS  read-only
	STATUS      current
	DESCRIPTION
		""
        ::= { uniSysDisp-Devices 20 }

uniSysDisp-Powers-PowerOut-Units OBJECT-TYPE
	SYNTAX      INTEGER {notAvailable (0), watt (1), kilowatt (2), decibel (3), percent (4), unused (-1)}
	MAX-ACCESS  read-only
	STATUS      current
	DESCRIPTION
		""
        ::= { uniSysDisp-Powers 3 }

uniSysDisp-Powers-PowerRef-Units OBJECT-TYPE
	SYNTAX      INTEGER {notAvailable (0), watt (1), kilowatt (2), decibel (3), percent (4), unused (-1)}
	MAX-ACCESS  read-only
	STATUS      current
	DESCRIPTION
		""
        ::= { uniSysDisp-Powers 6 }

uniSysDisp-Powers-PowerBallast OBJECT-TYPE
	SYNTAX      Integer32
	MAX-ACCESS  read-only
	STATUS      current
	DESCRIPTION
		"<unused>"
        ::= { uniSysDisp-Powers 7 }

uniSysDisp-Powers-PowerBallast-Divider OBJECT-TYPE
	SYNTAX      Integer32
	MAX-ACCESS  read-only
	STATUS      current
	DESCRIPTION
		"<unused>"
        ::= { uniSysDisp-Powers 8 }

uniSysDisp-Powers-PowerBallast-Units OBJECT-TYPE
	SYNTAX      INTEGER {notAvailable (0), watt (1), kilowatt (2), decibel (3), percent (4), unused (-1)}
	MAX-ACCESS  read-only
	STATUS      current
	DESCRIPTION
		"<unused>"
        ::= { uniSysDisp-Powers 9 }

uniSysDisp-Powers-PowerOut OBJECT-TYPE
	SYNTAX      Integer32
	MAX-ACCESS  read-only
	STATUS      current
	DESCRIPTION
		""
        ::= { uniSysDisp-Powers 1 }

uniSysDisp-Powers-PowerOut-Divider OBJECT-TYPE
	SYNTAX      Integer32
	MAX-ACCESS  read-only
	STATUS      current
	DESCRIPTION
		""
        ::= { uniSysDisp-Powers 2 }

uniSysDisp-Powers-PowerRef OBJECT-TYPE
	SYNTAX      Integer32
	MAX-ACCESS  read-only
	STATUS      current
	DESCRIPTION
		""
        ::= { uniSysDisp-Powers 4 }

uniSysDisp-Powers-PowerRef-Divider OBJECT-TYPE
	SYNTAX      Integer32
	MAX-ACCESS  read-only
	STATUS      current
	DESCRIPTION
		""
        ::= { uniSysDisp-Powers 5 }

uniSysDisp-Main-Global-Root-OID OBJECT-TYPE
	SYNTAX      OBJECT IDENTIFIER
	MAX-ACCESS  read-only
	STATUS      current
	DESCRIPTION
		"Transmitter's Global Root OID"
        ::= { uniSysDisp-Main 1 }

uniSysDisp-Main-Model-Root-OID OBJECT-TYPE
	SYNTAX      OBJECT IDENTIFIER
	MAX-ACCESS  read-only
	STATUS      current
	DESCRIPTION
		"Transmitter's Model Root OID"
        ::= { uniSysDisp-Main 2 }

uniSysDisp-Main-Model-Code OBJECT-TYPE
	SYNTAX      OCTET STRING
	MAX-ACCESS  read-only
	STATUS      current
	DESCRIPTION
		"Transmitter's Model Code"
        ::= { uniSysDisp-Main 3 }

uniSysDisp-Main-Model-Short OBJECT-TYPE
	SYNTAX      OCTET STRING
	MAX-ACCESS  read-only
	STATUS      current
	DESCRIPTION
		"Transmitter's Short Model (UTF8)"
        ::= { uniSysDisp-Main 4 }

uniSysDisp-Main-Model-Full OBJECT-TYPE
	SYNTAX      OCTET STRING
	MAX-ACCESS  read-only
	STATUS      current
	DESCRIPTION
		"Transmitter's Full Model (UTF8)"
        ::= { uniSysDisp-Main 5 }

uniSysDisp-Main-Model-Name OBJECT-TYPE
	SYNTAX      OCTET STRING
	MAX-ACCESS  read-only
	STATUS      current
	DESCRIPTION
		"Transmitter's Name/Location (UTF8)"
        ::= { uniSysDisp-Main 6 }

uniSysDisp-Main-Model-SerialNumber OBJECT-TYPE
	SYNTAX      Integer32
	MAX-ACCESS  read-only
	STATUS      current
	DESCRIPTION
		"Transmitter's Serial Number (0 - Disabled)"
        ::= { uniSysDisp-Main 7 }

uniSysDisp-Main-Model-Channel OBJECT-TYPE
	SYNTAX      Integer32
	MAX-ACCESS  read-only
	STATUS      current
	DESCRIPTION
		"Transmitter's Channel"
        ::= { uniSysDisp-Main 8 }

uniSysDisp-Main-Nominal-PowerOut-Watt OBJECT-TYPE
	SYNTAX      Integer32
	MAX-ACCESS  read-only
	STATUS      current
	DESCRIPTION
		"Transmitter's Typical PowerOut (Unit: 1 W)"
        ::= { uniSysDisp-Main 9 }

uniSysDisp-Main-Devices-Total-Count OBJECT-TYPE
	SYNTAX      Integer32
	MAX-ACCESS  read-only
	STATUS      current
	DESCRIPTION
		"Total Physical Devices in Transmitter"
        ::= { uniSysDisp-Main 10 }

uniSysDisp-Main-Devices-Connected-Count OBJECT-TYPE
	SYNTAX      Integer32
	MAX-ACCESS  read-only
	STATUS      current
	DESCRIPTION
		"Connected Physical Devices in Transmitter"
        ::= { uniSysDisp-Main 11 }

uniSysDisp-Main-Status-Warning OBJECT-TYPE
	SYNTAX      INTEGER {false(0), true(1)}
	MAX-ACCESS  read-only
	STATUS      current
	DESCRIPTION
		"Transmitter's Warning Status"
        ::= { uniSysDisp-Main 12 }

uniSysDisp-Main-Status-Failure OBJECT-TYPE
	SYNTAX      INTEGER {false(0), true(1)}
	MAX-ACCESS  read-only
	STATUS      current
	DESCRIPTION
		"Transmitter's Failure Status"
        ::= { uniSysDisp-Main 13 }

uniSysDisp-Main-SNMP-Device-ID OBJECT-TYPE
	SYNTAX      Integer32
	MAX-ACCESS  read-only
	STATUS      current
	DESCRIPTION
		"ID for SNMP logging to central server"
        ::= { uniSysDisp-Main 14 }

uniSysDisp-Main-Device-Type-ID OBJECT-TYPE
	SYNTAX      Integer32
	MAX-ACCESS  read-only
	STATUS      current
	DESCRIPTION
		"ID of Model Type"
        ::= { uniSysDisp-Main 15 }

uniSysDisp-Main-Optional-Demodulator-OID OBJECT-TYPE
	SYNTAX      OBJECT IDENTIFIER
	MAX-ACCESS  read-only
	STATUS      current
	DESCRIPTION
		"<unused>"
        ::= { uniSysDisp-Main 16 }

uniSysDisp-Main-Devices-Ignored-Count OBJECT-TYPE
	SYNTAX      Integer32
	MAX-ACCESS  read-only
	STATUS      current
	DESCRIPTION
		""
        ::= { uniSysDisp-Main 17 }


--- This file was generated by Triada-TV application
--- 08.06.2018 17:20:24

END
